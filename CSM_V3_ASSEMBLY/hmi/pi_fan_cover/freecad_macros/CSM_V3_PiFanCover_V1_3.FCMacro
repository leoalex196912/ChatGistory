# -*- coding: utf-8 -*-
# =============================================================================
# CSM V3 -- MODULE 10 HMI -- PI FAN COVER V1.1 (Part M10-P04)
# =============================================================================
# Flat plate that hangs below the Raspberry Pi 4 (opposite side from the
# Pi Carrier).  Carries a standard 30 x 30 x 10 mm 5 V fan that draws
# outside air through the round intake and exhausts toward the Pi's
# downward-facing components (SoC + RAM).
#
# AIRFLOW direction (mount the fan so its arrow points TOWARD the Pi):
#
#     outside air
#         |
#         v
#     Cover intake hole (D24)
#         |
#         v
#     Fan body (5 V, 30 x 30 x 10)
#         |
#         v
#     Pi 4 PCB (component side)  <-- cooling target
#
# Mount stack (top -> bottom):
#   Pi Carrier (M10-P03)
#     | -- M2.5 standoff into Pi Carrier (~10 mm)  -- from carrier kit
#   Pi 4 PCB
#     | -- M2.5 brass standoff (~11 mm)            -- user-supplied
#   Pi Fan Cover (this part)
#     | -- M2.5 x 25 mm screw heads (4x)           -- user-supplied
#
# Screw length math:
#     25 (screw)
#   -  3 (Cover plate)
#   - 11 (brass standoff)
#   -  2 (Pi PCB)
#   ---------------
#   =  9 mm thread engagement into the Pi Carrier standoff -- comfortable
#
# The 30 mm fan bolts to the Cover TOP face with M3 x 14 mm screws
# (typically supplied with the fan).  Fan body lives in the 11 mm gap
# between Cover and Pi PCB.
#
# V1.1 changes (engineering review of V1.0):
#   * Intake opening D22 -> D24 (more free area, lower pressure drop)
#   * 4 diagonal stiffening RIBS on top face, from each Pi mount toward
#     the central opening (reduces fan-induced vibration)
#   * Renamed fan_corner_to_center -> fan_hole_radius (readability)
#   * Wall-check label "Standoff clears fan body" -> "Fan clearance"
#   * Assembly text: "fan blows UP" -> "fan arrow points at Pi PCB"
#   * Removed connector-type assumption (any 2-wire fan works)
#   * Promoted hardcoded fan params into machine_datums.py
#
# Local frame (plate-local):
#   X = along Pi long axis
#   Y = across Pi
#   Z = vertical (Z=0 = plate top face, fan side; Z=-T = bottom face)
# =============================================================================

import FreeCAD, Part, math, os, sys
sys.path.insert(0, r"C:\3D-Project\00_PROJECT_OVERVIEW")
import machine_datums as MD

# ============================================================
# PART METADATA (CSM V3 macro standard header)
# ============================================================
PART_NUMBER     = "M10-P04"
PART_NAME       = "Pi Fan Cover"
VERSION         = "V1.3"
STATUS          = "RELEASE"
PART_ID         = "CSM_V3_PiFanCover_V1_3"
PRINT_QTY       = 1
PRINT_MATERIAL  = "PETG (PA12 production)"
PRINT_INFILL    = "100%"
PRINT_LAYER     = "0.20 mm"
PRINT_WALLS     = 4

# ============================================================
# Helpers
# ============================================================
def cut_cylinder(shape, diameter, length, origin, direction=FreeCAD.Vector(0, 0, 1)):
    cyl = Part.makeCylinder(diameter / 2.0, length, origin, direction)
    return shape.cut(cyl)

def cut_box(shape, w, d, h, origin):
    box = Part.makeBox(w, d, h, origin)
    return shape.cut(box)

def capsule_face(w, l):
    """Stadium-shape face in XY plane, centered on origin.
    Width w (X), length l (Y); two semicircles of radius w/2 at the ends."""
    r = w / 2.0
    hl = l / 2.0
    p_top_right = FreeCAD.Vector( r,  hl - r, 0)
    p_top_mid   = FreeCAD.Vector( 0,  hl,     0)
    p_top_left  = FreeCAD.Vector(-r,  hl - r, 0)
    p_bot_left  = FreeCAD.Vector(-r, -hl + r, 0)
    p_bot_mid   = FreeCAD.Vector( 0, -hl,     0)
    p_bot_right = FreeCAD.Vector( r, -hl + r, 0)
    edges = [
        Part.Arc(p_top_right, p_top_mid, p_top_left).toShape(),
        Part.LineSegment(p_top_left, p_bot_left).toShape(),
        Part.Arc(p_bot_left, p_bot_mid, p_bot_right).toShape(),
        Part.LineSegment(p_bot_right, p_top_right).toShape(),
    ]
    return Part.Face(Part.Wire(edges))

def rounded_rect_face(w, d, r):
    """Filleted-corner rectangle face in XY plane, centered on origin."""
    hw, hd = w / 2.0, d / 2.0
    p1 = FreeCAD.Vector(-hw + r, -hd, 0)
    p2 = FreeCAD.Vector( hw - r, -hd, 0)
    p3 = FreeCAD.Vector( hw,     -hd + r, 0)
    p4 = FreeCAD.Vector( hw,      hd - r, 0)
    p5 = FreeCAD.Vector( hw - r,  hd, 0)
    p6 = FreeCAD.Vector(-hw + r,  hd, 0)
    p7 = FreeCAD.Vector(-hw,      hd - r, 0)
    p8 = FreeCAD.Vector(-hw,     -hd + r, 0)
    c_BR = FreeCAD.Vector( hw - r, -hd + r, 0)
    c_TR = FreeCAD.Vector( hw - r,  hd - r, 0)
    c_TL = FreeCAD.Vector(-hw + r,  hd - r, 0)
    c_BL = FreeCAD.Vector(-hw + r, -hd + r, 0)
    m_BR = c_BR + FreeCAD.Vector(r * math.cos(-math.pi/4), r * math.sin(-math.pi/4), 0)
    m_TR = c_TR + FreeCAD.Vector(r * math.cos( math.pi/4), r * math.sin( math.pi/4), 0)
    m_TL = c_TL + FreeCAD.Vector(r * math.cos( 3*math.pi/4), r * math.sin( 3*math.pi/4), 0)
    m_BL = c_BL + FreeCAD.Vector(r * math.cos(-3*math.pi/4), r * math.sin(-3*math.pi/4), 0)
    edges = [
        Part.LineSegment(p1, p2).toShape(),
        Part.Arc(p2, m_BR, p3).toShape(),
        Part.LineSegment(p3, p4).toShape(),
        Part.Arc(p4, m_TR, p5).toShape(),
        Part.LineSegment(p5, p6).toShape(),
        Part.Arc(p6, m_TL, p7).toShape(),
        Part.LineSegment(p7, p8).toShape(),
        Part.Arc(p8, m_BL, p1).toShape(),
    ]
    return Part.Face(Part.Wire(edges))

# ============================================================
# Geometry parameters -- all from machine_datums.py (HMI block)
# ============================================================
PLATE_W       = MD.HMI_PI_FAN_COVER_W
PLATE_D       = MD.HMI_PI_FAN_COVER_D
PLATE_T       = MD.HMI_PI_FAN_COVER_T

# Pi 4 mount interface (same as Pi Carrier's Pi-side PCD)
PI_PCD_X      = MD.HMI_PI4_PCD_X                 # 58 mm
PI_PCD_Y      = MD.HMI_PI4_PCD_Y                 # 49 mm
M2_5_CLEAR_D  = MD.HMI_M2_5_CLEAR_D              # 3.0 mm

# 30 x 30 x 10 fan
FAN_OPENING_D = MD.HMI_PI_FAN_OPENING_D          # 24 mm round intake (V1.1)
FAN_MOUNT_PCD = MD.HMI_PI_FAN_MOUNT_PCD          # 24 mm screw spacing
M3_CLEAR_D    = MD.HMI_PI_FAN_M3_CLEAR_D         # 3.5 mm
FAN_BODY_W    = MD.HMI_PI_FAN_BODY_W             # 30 mm
FAN_BODY_H    = MD.HMI_PI_FAN_BODY_H             # 10 mm
FAN_VOLTAGE   = MD.HMI_PI_FAN_VOLTAGE            # 5 V from Pi GPIO
STANDOFF_H    = MD.HMI_PI_FAN_STANDOFF_H         # 11 mm Pi-to-Cover spacer

# V1.1: stiffening ribs to suppress fan-induced plate resonance
RIB_W         = MD.HMI_PI_FAN_RIB_W              # 2.0 mm wide
RIB_H         = MD.HMI_PI_FAN_RIB_H              # 1.5 mm tall (above top face)

# V1.2: slotted grille (replaces single round opening)
GRILLE_SLOTS  = MD.HMI_PI_FAN_GRILLE_SLOTS       # 5
GRILLE_SLOT_W = MD.HMI_PI_FAN_GRILLE_SLOT_W      # 3.5 mm slot width
GRILLE_SLOT_H = MD.HMI_PI_FAN_GRILLE_SLOT_H      # 22 mm slot length
GRILLE_WALL   = MD.HMI_PI_FAN_GRILLE_WALL        # 1.6 mm between slots

# V1.2: plate corner fillet
CORNER_R      = MD.HMI_PI_FAN_CORNER_R           # 3.0 mm

# V1.3: M3 counterbore on bottom face (pan-head sits flush)
M3_CB_D       = MD.HMI_PI_FAN_M3_CB_D            # 6.0 mm
M3_CB_H       = MD.HMI_PI_FAN_M3_CB_H            # 1.5 mm

# V1.3: orientation-tolerant cable channels (+X and -X radial slots on top
# face).  Replaces V1.2's single corner notch.
CABLE_CH_W    = MD.HMI_PI_FAN_CABLE_CH_W         # 4.0 mm (Y dimension)
CABLE_CH_L    = MD.HMI_PI_FAN_CABLE_CH_L         # 6.0 mm extending from fan
CABLE_CH_D    = MD.HMI_PI_FAN_CABLE_CH_D         # 1.5 mm depth (into top)

# Pi heatsink (V1.3: was 0, now realistic low-profile default 6 mm)
HEATSINK_H    = MD.HMI_PI_HEATSINK_H_NOMINAL     # 6 mm

# Boolean / overcut helpers
EPS_OVERCUT   = MD.HMI_BOOLEAN_OVERCUT
CUT_EXTRA     = MD.HMI_CUT_EXTRA

# ============================================================
# Standard CSM V3 banner
# ============================================================
print("=" * 70)
print(f"CSM V3   Part {PART_NUMBER}   {PART_NAME}   {VERSION}   [{STATUS}]")
print("=" * 70)
print(f"  Material:   {PRINT_MATERIAL}")
print(f"  Print:      {PRINT_INFILL} infill, {PRINT_WALLS} walls, {PRINT_LAYER} layers")
print(f"  Quantity:   {PRINT_QTY}")
print()
print("WALL-THICKNESS CHECK:")
plate_edge_to_pi_hole_x   = PLATE_W / 2.0 - PI_PCD_X / 2.0 - M2_5_CLEAR_D / 2.0
plate_edge_to_pi_hole_y   = PLATE_D / 2.0 - PI_PCD_Y / 2.0 - M2_5_CLEAR_D / 2.0
plate_edge_to_fan_hole_x  = PLATE_W / 2.0 - FAN_MOUNT_PCD / 2.0 - M3_CLEAR_D / 2.0
plate_edge_to_fan_hole_y  = PLATE_D / 2.0 - FAN_MOUNT_PCD / 2.0 - M3_CLEAR_D / 2.0
fan_hole_radius           = math.sqrt(2.0) * FAN_MOUNT_PCD / 2.0      # 17.0 mm
# V1.2: grille is centered, half-width = (N*W + (N-1)*WALL)/2
grille_half_w             = (GRILLE_SLOTS * GRILLE_SLOT_W +
                             (GRILLE_SLOTS - 1) * GRILLE_WALL) / 2.0
grille_edge_to_fan_hole   = fan_hole_radius - grille_half_w - M3_CLEAR_D / 2.0
pi_hole_distance          = math.sqrt((PI_PCD_X/2 - FAN_MOUNT_PCD/2)**2 +
                                      (PI_PCD_Y/2 - FAN_MOUNT_PCD/2)**2)
pi_hole_to_fan_hole       = pi_hole_distance - M2_5_CLEAR_D/2 - M3_CLEAR_D/2
fan_clearance             = STANDOFF_H - FAN_BODY_H                    # 1.0 mm
heatsink_clearance        = STANDOFF_H - HEATSINK_H                    # Pi side
checks = [
    ("Plate edge to Pi mount hole (X)",   plate_edge_to_pi_hole_x,   2.0),
    ("Plate edge to Pi mount hole (Y)",   plate_edge_to_pi_hole_y,   2.0),
    ("Plate edge to fan mount hole (X)",  plate_edge_to_fan_hole_x,  2.0),
    ("Plate edge to fan mount hole (Y)",  plate_edge_to_fan_hole_y,  2.0),
    ("Grille edge to fan mount hole",     grille_edge_to_fan_hole,   2.0),
    ("Pi mount to fan mount diagonal",    pi_hole_to_fan_hole,       5.0),
    ("Fan clearance (standoff - body)",   fan_clearance,             0.5),
    ("Pi heatsink envelope (info)",       heatsink_clearance,        0.5),
    ("Grille slot wall thickness",        GRILLE_WALL,               1.6),
]
for label, val, min_ok in checks:
    flag = "OK " if val >= min_ok else "!! "
    print(f"  {flag}{label:42s} {val:6.2f} mm  (min {min_ok})")
print()
print("GEOMETRY:")
print(f"  plate:          {PLATE_W} x {PLATE_D} x {PLATE_T} mm")
print(f"  Pi interface:   4x M2.5 clearance at PCD {PI_PCD_X} x {PI_PCD_Y} (Pi 4 native)")
print(f"  fan interface:  4x M3 clearance at PCD {FAN_MOUNT_PCD} x {FAN_MOUNT_PCD}")
print(f"  intake grille:  {GRILLE_SLOTS} capsule slots x {GRILLE_SLOT_W} x {GRILLE_SLOT_H} mm")
print(f"  fan target:     {FAN_BODY_W} x {FAN_BODY_W} x {FAN_BODY_H} mm, 5 V brushless")
print(f"  spacer height:  {STANDOFF_H} mm M2.5 brass standoffs (Pi to Cover)")
print(f"  corner fillet:  R{CORNER_R}")
print(f"  fan screw CB:   D{M3_CB_D} x {M3_CB_H} on BOTTOM face")
print(f"  cable channels: 2x {CABLE_CH_W} x {CABLE_CH_L} x {CABLE_CH_D} (+X and -X)")
print()
# V1.3: airflow metrics block
fan_area      = FAN_BODY_W * FAN_BODY_W
grille_area   = GRILLE_SLOTS * GRILLE_SLOT_W * GRILLE_SLOT_H
restriction   = (1.0 - grille_area / fan_area) * 100.0
print("COOLING:")
print(f"  fan footprint area:    {fan_area:6.0f} mm^2 ({FAN_BODY_W} x {FAN_BODY_W})")
print(f"  grille free area:      {grille_area:6.0f} mm^2 ({GRILLE_SLOTS} x {GRILLE_SLOT_W:.1f} x {GRILLE_SLOT_H:.1f})")
print(f"  open fraction:         {100*grille_area/fan_area:5.1f} %")
print(f"  restriction:           {restriction:5.1f} %  (target < 60 %)")
print()

doc = FreeCAD.newDocument(PART_ID)

# ============================================================
# Build plate
# Plate top face at Z=0 (fan-side), bottom face at Z=-PLATE_T
# ============================================================
# V1.2: rounded-corner sketch + extrude (guaranteed fillets)
plate_face = rounded_rect_face(PLATE_W, PLATE_D, CORNER_R)
plate_face.translate(FreeCAD.Vector(0, 0, -PLATE_T))
plate = plate_face.extrude(FreeCAD.Vector(0, 0, PLATE_T))

# Pi mount holes (4 corners of PCD 58 x 49)
for sx in (-1, +1):
    for sy in (-1, +1):
        hx = sx * (PI_PCD_X / 2.0)
        hy = sy * (PI_PCD_Y / 2.0)
        plate = cut_cylinder(plate, M2_5_CLEAR_D, PLATE_T + 2 * CUT_EXTRA,
                              FreeCAD.Vector(hx, hy, -PLATE_T - CUT_EXTRA))

# Fan mount holes (4 corners of PCD 24 x 24) with bottom-face counterbore
# for M3 pan-head screws (heads recessed, no wire snagging)
for sx in (-1, +1):
    for sy in (-1, +1):
        hx = sx * (FAN_MOUNT_PCD / 2.0)
        hy = sy * (FAN_MOUNT_PCD / 2.0)
        # Through-hole
        plate = cut_cylinder(plate, M3_CLEAR_D, PLATE_T + 2 * CUT_EXTRA,
                              FreeCAD.Vector(hx, hy, -PLATE_T - CUT_EXTRA))
        # V1.3: counterbore from bottom face (Z = -PLATE_T upward)
        plate = cut_cylinder(plate, M3_CB_D, M3_CB_H + EPS_OVERCUT,
                              FreeCAD.Vector(hx, hy, -PLATE_T - EPS_OVERCUT))

# V1.3: CAPSULE-slot grille (rounded ends, no internal sharp corners)
# Built from rounded_rect_face with r = slot_W / 2 -> full stadium shape.
slot_pitch = GRILLE_SLOT_W + GRILLE_WALL
total_w    = GRILLE_SLOTS * GRILLE_SLOT_W + (GRILLE_SLOTS - 1) * GRILLE_WALL
x0         = -total_w / 2.0 + GRILLE_SLOT_W / 2.0
for i in range(GRILLE_SLOTS):
    cx = x0 + i * slot_pitch
    slot_face = capsule_face(GRILLE_SLOT_W, GRILLE_SLOT_H)
    slot_face.translate(FreeCAD.Vector(cx, 0, -PLATE_T - CUT_EXTRA))
    slot = slot_face.extrude(FreeCAD.Vector(0, 0, PLATE_T + 2 * CUT_EXTRA))
    plate = plate.cut(slot)

# V1.3: ORIENTATION-TOLERANT cable channels (replaces single corner notch).
# 2 radial channels cut into top face: +X and -X.  User rotates the fan so
# its wire exit aligns with one of these channels.  Depth 1.5 mm leaves
# 1.5 mm of plate underneath (no through-cut).
channel_y_half = CABLE_CH_W / 2.0
channel_z0 = -CABLE_CH_D
channel_zh = CABLE_CH_D + EPS_OVERCUT
ch_inner_x = FAN_BODY_W / 2.0                        # 15 mm (just outside fan body)
for sx in (-1, +1):
    if sx > 0:
        x_lo = ch_inner_x
        x_hi = ch_inner_x + CABLE_CH_L
    else:
        x_lo = -ch_inner_x - CABLE_CH_L
        x_hi = -ch_inner_x
    plate = cut_box(plate, x_hi - x_lo, CABLE_CH_W, channel_zh,
                     FreeCAD.Vector(x_lo, -channel_y_half, channel_z0))

# V1.1: 4 diagonal stiffening RIBS on top face (Z = 0 to RIB_H),
# from each Pi mount toward the central opening.  Ends short of the
# fan footprint (30 x 30 centered at origin) so they don't fight the
# fan body.
def make_rib(sx, sy):
    start_pt = FreeCAD.Vector(sx * PI_PCD_X / 2.0, sy * PI_PCD_Y / 2.0, 0)
    # Direction toward origin
    L_full = math.hypot(start_pt.x, start_pt.y)
    ux, uy = -start_pt.x / L_full, -start_pt.y / L_full
    # Stop the rib just outside the 30 mm fan footprint corner
    # (and outside the intake opening with margin)
    # Maximum length where rib stays outside both fan body and opening:
    #   along the rib, X reaches sign(sx) * FAN_BODY_W/2 at d = (|start_pt.x| - 15) / |ux|
    #   along the rib, Y reaches sign(sy) * FAN_BODY_W/2 at d = (|start_pt.y| - 15) / |uy|
    dx_lim = (abs(start_pt.x) - FAN_BODY_W / 2.0) / abs(ux)
    dy_lim = (abs(start_pt.y) - FAN_BODY_W / 2.0) / abs(uy)
    rib_length = min(dx_lim, dy_lim) - 1.0  # 1 mm safety from fan footprint
    end_pt = FreeCAD.Vector(start_pt.x + rib_length * ux,
                            start_pt.y + rib_length * uy, 0)
    # Perpendicular vector for rib width
    px, py = -uy, ux
    c1 = FreeCAD.Vector(start_pt.x + px * RIB_W/2, start_pt.y + py * RIB_W/2, 0)
    c2 = FreeCAD.Vector(end_pt.x   + px * RIB_W/2, end_pt.y   + py * RIB_W/2, 0)
    c3 = FreeCAD.Vector(end_pt.x   - px * RIB_W/2, end_pt.y   - py * RIB_W/2, 0)
    c4 = FreeCAD.Vector(start_pt.x - px * RIB_W/2, start_pt.y - py * RIB_W/2, 0)
    wire = Part.makePolygon([c1, c2, c3, c4, c1])
    face = Part.Face(wire)
    return face.extrude(FreeCAD.Vector(0, 0, RIB_H))

for sx in (-1, +1):
    for sy in (-1, +1):
        plate = plate.fuse(make_rib(sx, sy))
# V1.3: single removeSplitter pass after all ribs (faster than per-fuse)
plate = plate.removeSplitter()

# V1.2: corner fillets are built into the plate sketch (rounded_rect_face)
# -- no post-boolean fillet pass needed.

# Export
obj = doc.addObject("Part::Feature", PART_ID)
obj.Shape = plate
if FreeCAD.GuiUp and obj.ViewObject is not None:
    obj.ViewObject.ShapeColor = (0.55, 0.70, 0.85)
doc.recompute()

# V1.2: read shape back from the document after recompute, so the volume
# and CoM we print match exactly what gets exported.
plate = obj.Shape

BASE = os.path.dirname(os.path.dirname(os.path.abspath(__file__)))
OUT_STL  = os.path.join(BASE, PART_ID + ".stl")
OUT_STEP = os.path.join(BASE, PART_ID + ".step")
Part.export([obj], OUT_STL)
Part.export([obj], OUT_STEP)

try:
    com = plate.CenterOfMass
except AttributeError:
    com = plate.Solids[0].CenterOfMass if plate.Solids else None
print(f"[OK] STL:  {OUT_STL}")
print(f"[OK] STEP: {OUT_STEP}")
print(f"     volume: {plate.Volume:.0f} mm^3  (~{plate.Volume*1.27/1000:.1f}g PETG)")
if com is not None:
    print(f"     center of mass (plate-local):  X={com.x:+.2f}  Y={com.y:+.2f}  Z={com.z:+.2f} mm")
print()
print("ASSEMBLY (after Pi is mounted on Pi Carrier per M10-P03 step 5):")
print(" 1. Print PETG flat on bed, 100% infill, 4 walls, 0.2 mm layers")
print(" 2. Have ready: 4x M2.5 brass standoffs (11 mm, female-female)")
print("                4x M2.5 x 25 mm socket-head screws")
print("                4x M3 x 14 mm screws (usually supplied with fan)")
print("                1x 30 x 30 x 10 mm 5 V fan")
print(" 3. REMOVE the four M2.5 x 6 mm screws holding the Pi to the Pi")
print("    Carrier standoffs (do NOT detach the Pi standoffs from carrier)")
print(" 4. Thread the 4x 11 mm brass standoffs onto the BOTTOM of the Pi")
print("    Carrier standoffs through the Pi PCB holes -- they sandwich the")
print("    Pi between the carrier standoffs (above) and these (below)")
print(" 5. Mount the fan to the Cover TOP face with 4x M3 x 14 screws into")
print("    the 4 fan mount holes (PCD 24 x 24); the airflow ARROW on the")
print("    fan side must POINT TOWARD THE PI PCB (away from the Cover plate)")
print(" 6. Position the Cover under the Pi: align Cover Pi-mount holes with")
print("    the 11 mm standoffs; pass 4x M2.5 x 25 screws UP from BELOW the")
print("    Cover into the 11 mm standoff threads")
print(" 7. Connect fan power leads to Pi GPIO header:")
print("    - Red wire   -> Pin 4 (+5V)")
print("    - Black wire -> Pin 6 (GND)")
print("    (any 2-wire 5 V fan works -- connector style is irrelevant)")
print(" 8. Verify the fan spins on Pi power-up; confirm airflow direction")
print("    is TOWARD the Raspberry Pi PCB (matches the molded arrow on the")
print("    fan side).  Rotate the fan so its wire exit aligns with whichever")
print("    cable channel (+X or -X side of the cover) gives the cleanest")
print("    route to the Pi GPIO header.")
print("=" * 70)
