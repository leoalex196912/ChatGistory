# -*- coding: utf-8 -*-
# =============================================================================
# CSM V3 -- CYLINDER V3.1  (Erlbacher-pattern, optimized slot depth)
# =============================================================================
# File:    CSM_V3_Cylinder_V3_0.FCMacro  (filename unchanged, version bumped internally)
# Date:    2026-05-24
# Output:  C:\3D-Project\01_MECHANICAL\02_CASSETTE_HEAD\cylinder\
#
# WHAT CHANGED FROM V3.0 (V3.1, 2026-05-24)
# -----------------------------------------
# Phase-1 physical test of WEDGE_B V2 (10-slot fine sweep 3.50..5.30 mm)
# proved that:
#   slot 7 (4.70 mm, groove 3.10) = BEST needle retention
#   slot 6 (4.50 mm, groove 2.90) = TIE / acceptable fallback
#   slot 8 (4.90 mm, groove 3.30) = LOOSE (over-depth)
# Locked production values:
#   SLOT_DEPTH         = 4.70 mm  (was 3.00 mm in V3.0)
#   SPRING_GROOVE_DEPTH = 3.10 mm (was 1.30 mm in V3.0)
# Both maintain +0.20 mm spring preload on needle stem.
# Spring is now RECESSED 0.31 mm below OD (was protruding 1.49 mm in V3.0)
# -- no cam ring interference risk.
# Wall material remaining at slot bottom: 8.45 mm (plenty).
# V3.0 STLs archived in _archive/v3_0_locked_2026-05-19/
#
# WHAT CHANGED FROM V2.0 (V3.0, May 2026)
# ----------------------------------------
# V2.0 had a stepped slot: narrow 1.22mm slot from Z=23-75 + wider 8.5mm
# "butt cavity" from Z=19-23. That step physically prevented the needle butt
# from completing the cam ring's 8mm lift cycle -- the butt would slam into
# the step at Z=23. Machine would deadlock at full stitch position.
#
# V3.0 matches the Erlbacher cylinder photograph exactly:
#   - Slots run UNIFORM full cylinder height (Z=0 to Z=75)
#   - All slots identical: 1.22mm wide x 2.0mm deep x 75mm tall
#   - NO stepped butt cavity -- needle butt's radial L-protrusion exits
#     the slot past OD and engages cam ring V6.5's internal track directly
#   - Slots are open at both top (hook protrudes) and bottom (needle install)
#
# Compatibility:
#   - Cam Ring V6.5 (locked): 115mm ID, engages butts at Z=19-31 -- OK
#   - Sinker Ring V1.0 (locked): sits on top face at Z=75 -- OK
#   - Drive Hub V1.3 (locked): 18mm boss into bottom pocket -- OK
#   - FlyDesigns 12g needle: 1.15x1.80mm stem in 1.22x2.00mm slot -- OK
# =============================================================================

import FreeCAD, Part, math, os

# =============================================================================
# OUTPUT PATHS
# =============================================================================
BASE = r"C:\3D-Project\01_MECHANICAL\02_CASSETTE_HEAD\cylinder"
PATH_STL = os.path.join(BASE, "CSM_V3_Cylinder_V3_1_FULL.stl")
PATH_STL_WEDGE_A = os.path.join(BASE, "CSM_V3_Cylinder_V3_1_WEDGE_A_WIDTH.stl")
PATH_STL_WEDGE_B = os.path.join(BASE, "CSM_V3_Cylinder_V3_1_WEDGE_B_DEPTH.stl")
PATH_PNG_ISO = os.path.join(BASE, "images", "Cylinder_V3_0_ISO.png")
PATH_PNG_TOP = os.path.join(BASE, "images", "Cylinder_V3_0_TOP.png")
PATH_PNG_FRONT = os.path.join(BASE, "images", "Cylinder_V3_0_FRONT.png")
PATH_PNG_WEDGE = os.path.join(BASE, "images", "Cylinder_V3_0_WEDGE_ISO.png")
PATH_SVG = os.path.join(BASE, "blueprints", "Cylinder_V3_0_Blueprint.svg")

for p in [PATH_STL, PATH_STL_WEDGE_A, PATH_STL_WEDGE_B,
          PATH_PNG_ISO, PATH_PNG_TOP, PATH_PNG_FRONT, PATH_PNG_WEDGE, PATH_SVG]:
    os.makedirs(os.path.dirname(p), exist_ok=True)

# =============================================================================
# PARAMETERS (Erlbacher-compatible, 12-gauge FlyDesigns needles)
# =============================================================================

# Cylinder body
CYL_OD       = 114.3   # Legare 4.5" standard
CYL_ID       = 88.0    # bore -- clears Drive Hub boss, sock take-down opening
CYL_HEIGHT   = 75.0    # standard Legare working height

# Bottom mounting RING (not a solid floor -- keeps sock take-down open)
# WHY: PCD 70mm bolts (radius 35mm) are INSIDE the D88mm bore (radius 44mm).
# Without material at the bottom, the bolt pockets cut empty space.
# A full floor would block sock take-down (the knitted tube hangs through
# the bore with a weight to maintain tension -- Erlbacher uses this).
# A RING gives both: material around PCD 70mm for bolts + central opening
# for the sock + take-down weight to pass through.
BOTTOM_THICK    = 12.0    # ring thickness (>= INSERT_HOLE_H + 2mm safety)
TAKEDOWN_OPEN_D = 50.0    # central opening D through the bottom ring
                           # 50mm gives plenty of room for sock + weight,
                           # leaves ~7mm material between opening and bolt
                           # insert (insert OD 6mm at radius 35, opening at
                           # radius 25 -> 10mm-5mm/2 = 7mm material around)

# Needle slots: full-height with UNIFORM RADIAL DEPTH (smooth needle path)
# but CIRCUMFERENTIAL WIDTH changes -- narrow body for stem retention,
# wider at top for yarn/hook/latch clearance.
SLOT_COUNT   = 72
SLOT_WIDTH   = 1.22    # circumferential  (1.15mm needle + 0.07mm clearance)
SLOT_DEPTH   = 4.70    # radial inward.  PHASE-1 PHYSICAL TEST RESULT
                       # (V3.1, 2026-05-24): WEDGE_B V2 print + needle test
                       # showed slot 7 (4.70 mm) = BEST retention,
                       # slot 6 (4.50) = tie, slot 8 (4.90) = loose.
                       # Older V3.0 value was 3.00 mm — see _archive folder.
                       # Spring is recessed 0.31 mm below OD with this depth
                       # (no protrusion past cam ring ID 115). Wall material
                       # remaining = 8.45 mm at slot bottom — stiff.
SLOT_ROOT_FILLET = 0.5 # mm  fillet radius at slot-bottom internal corners.
                       # CRITICAL for PETG fatigue life: sharp 90 deg internal
                       # corners along layer lines are classic crack starters
                       # under cyclic cam loading. 0.4-0.6mm is the right
                       # range for 0.4mm nozzle + 0.16-0.20mm layer height.
# Top zone -- WIDER slot for yarn/hook/latch clearance (does NOT hold needle)
# This is the visible "wide slot" band at the top of Erlbacher/tru-knit cylinders.
# Below this zone the slot narrows to SLOT_WIDTH to grip the needle stem.
# IMPORTANT: this only widens the CIRCUMFERENTIAL width, not the radial DEPTH.
# Slot depth stays uniform 4.20mm full height -- needle path remains smooth.
TOP_ZONE_WIDTH   = 3.00   # mm  slot width in top zone (vs 1.22mm in body)
                           # Reduced from 3.5 -- gives fin width of 1.99mm at
                           # top (was 1.49mm). Stronger fin tips, less risk of
                           # chip from yarn/latch impacts.
TOP_ZONE_HEIGHT  = 6.0    # mm  axial height of the wide top zone
                           # Reduced from 8.0 -- longer stiff section above
                           # spring groove, less unsupported fin length.
TOP_TRANSITION_H = 2.0    # mm  smooth chamfer between wide top and narrow body

# Fin-top easing: the cutter widens by FIN_TOP_CHAMFER per side over the top
# FIN_TOP_CHAMFER_H mm of the slot. This GUARANTEES visibly eased fin-top
# corners because the chamfer is carved INTO the geometry by the same
# boolean that cuts the slot -- not added as a post-process step (which
# silently fails on this complex post-boolean geometry).
# At top face: slot is (TOP_ZONE_WIDTH + 2*FIN_TOP_CHAMFER) wide
#              = 3.00 + 1.20 = 4.20mm
# Fin width at top face: 4.987 - 4.20 = 0.787mm (chamfered tip, not knife edge
# because the chamfer is a flat slope, not a peak)
FIN_TOP_CHAMFER   = 0.6   # mm  per-side widening at the top (each fin side
                           # of every slot opening gets a 0.6mm chamfer)
FIN_TOP_CHAMFER_H = 0.8   # mm  axial height over which the flare happens

# Front-to-back (radial) easing of the fin top:
# - OD_TOP_CHAMFER:    radial chamfer where fin top meets the OD outer wall
# - BORE_TOP_CHAMFER:  radial chamfer where fin top meets the bore inner wall
# Both are carved by cone-based boolean subtracts (NOT post-cut chamfer)
# so the operation is robust against OCC failure modes.
OD_TOP_CHAMFER    = 0.8   # mm  OD outer top edge chamfer (yarn glides over)
BORE_TOP_CHAMFER  = 1.0   # mm  bore inner top edge chamfer (loop transfer)

# Spring groove (FlyDesigns 0.110" / 2.79mm spring wire)
# Position per Erlbacher photo: upper portion of cylinder, above the cam
# engagement zone (Z=19-31), below the top yarn-catch zone.
# Width 4.0mm gives 1.2mm axial play -- easy to thread spring around cylinder.
# Depth 2.2mm leaves spring protruding ~0.59mm past OD -- enough to engage
# needle stems firmly but not enough to snag yarn carriers.
SPRING_GROOVE_W     = 4.0    # axial width   (2.79mm wire + 1.21mm install slack)
SPRING_GROOVE_DEPTH = 3.10   # radial depth -- V3.1 LOCKED.
                              # Coupled to SLOT_DEPTH=4.70 mm:
                              #   groove_depth = slot_depth - 1.6  (for +0.20 mm preload)
                              # With slot=4.70 mm:
                              #   needle outer face at radius 54.25 mm
                              #   spring inner face at radius 54.05 mm
                              #   geometric preload = 0.20 mm  (positive, retains needle)
                              # Spring is RECESSED 0.31 mm below cylinder OD
                              # (2.79 mm wire - 3.10 mm groove = -0.31).
                              # NO interference with cam ring ID 115.
                              # Old V3.0 was 1.30 mm (spring protruded 1.49 mm past OD).
SPRING_GROOVE_Z_CTR = 55.0   # mm from bottom -- matches visible band in photo
SPRING_GROOVE_Z_BOT = SPRING_GROOVE_Z_CTR - SPRING_GROOVE_W / 2.0   # 53.0
SPRING_GROOVE_Z_TOP = SPRING_GROOVE_Z_CTR + SPRING_GROOVE_W / 2.0   # 57.0

# Drive hub interface
HUB_POCKET_D    = 18.20   # 18mm boss + 0.20mm slip fit
HUB_POCKET_H    = 3.0     # pocket depth
HUB_POCKET_CHAM = 0.5     # lead-in chamfer at pocket entry

# Bolt pattern -- matches Drive Hub V2.4.2 (B0DPQJ4W3Z heat-set inserts)
# Drive hub has 4x M5 flathead bolts coming UP from below, threading into
# M5 brass heat-set inserts pressed into the BOTTOM face of this cylinder.
BOLT_COUNT     = 4
BOLT_PCD       = 70.0    # matches drive hub bolt circle
BOLT_ANGLE_OFF = 45.0    # 45 deg offset matches drive hub (clears clamp slot)
INSERT_HOLE_D  = 6.0     # M5 heat-set insert pocket (insert OD ~6.4mm,
                          # hole 6.0mm allows brass to melt into PETG for grip)
INSERT_HOLE_H  = 10.0    # depth (insert is ~9.5mm long, 0.5mm overshoot)

# Edge treatment -- ALL fin top corners eased, not just OD outer ring.
# Each fin top has 4 edges around it (outer arc, inner arc, 2 slot sides).
# Easing all of them eliminates the sharp "teeth" look, makes the cylinder
# safer to handle, and gives smoother yarn glide at high RPM.
# 0.6mm fits the narrowest feature (1.99mm fin width at top zone).
TOP_EDGE_CHAMFER = 0.6   # mm  chamfer on ALL top-face edges (fin tops eased)
BOT_EDGE_CHAMFER = 0.6   # mm  bottom OD edge chamfer (edge-break)

# Hall sensor indexing magnet pocket (one pulse per revolution).
# Placed on the bottom face, in the ring material at PCD 70mm (same as bolt
# inserts), at angle 0 deg (midway between bolt inserts at 45 and 315 deg).
# Cheap to add now; expensive to retrofit later.
MAGNET_POCKET_D  = 6.0   # mm  D6 neodymium magnet OD (B0F4KS6KV3 N52, in stock)
MAGNET_POCKET_H  = 2.2   # mm  pocket depth -- magnet is 2.0mm thick;
                          # +0.2mm for epoxy bed + flush retention.
                          # Use cyanoacrylate or 5-min epoxy on install.
MAGNET_PCD       = 95.0  # mm  OUTSIDE bolt circle so it's visually distinct
                          # from the 4 insert pockets. Sits in ring material
                          # between bolt PCD 70 and slot bottoms at radius
                          # 54.15mm (slot floor with SLOT_DEPTH=3.0mm).
                          # Magnet pocket center at radius 47.5mm -- 12.5mm
                          # inside bolt center, 6.25mm clear of slot bottom.
MAGNET_ANGLE_DEG = 0.0   # mm  arbitrary angular position (one pulse/rev)

# TWO TEST WEDGES with isolated variables (proper experimental design).
# Print BOTH before the full cylinder, ~30-45 min + ~10g PETG each.
#
# WEDGE A -- WIDTH SWEEP at fixed depth 3.0mm:
#   Finds the right slot WIDTH for your printer + filament.
#   Hold depth constant so you can isolate the width effect.
#
# WEDGE B -- DEPTH SWEEP at fixed width 1.22mm:
#   Finds the right slot DEPTH (includes the reference cylinder's 2.55mm
#   depth as the shallowest test).
#   Hold width constant to isolate depth effect on fin flex / needle fit.
#
# After printing, push a 12g FlyDesigns needle through each slot:
#   - WEDGE A: pick the slot that slides smoothly with no lateral rattle
#   - WEDGE B: pick the slot where the fin doesn't flex under butt-side
#              pressure but the needle still slides freely
WEDGE_ANGLE_DEG = 30.0

WEDGE_A_SLOTS = [   # WIDTH sweep at fixed depth 3.0
    # (slot_width_mm, slot_depth_mm)
    (1.18, 3.0),
    (1.20, 3.0),
    (1.22, 3.0),    # <-- baseline (matches SLOT_WIDTH)
    (1.24, 3.0),
    (1.26, 3.0),
    (1.28, 3.0),
]

WEDGE_B_SLOTS = [   # V2 (2026-05-24): fine sweep 3.50..5.30 mm at 0.20 mm steps
    # Each entry is (slot_width_mm, slot_depth_mm, groove_depth_mm).
    # Groove depth chosen for constant +0.20 mm spring preload:
    #     groove_depth = slot_depth - 1.8 + 0.2 = slot_depth - 1.6
    # Physical test results from V1 wedge (May 19 print):
    #   - Slots 4 (4.0 mm) and 5 (4.5 mm) worked WELL
    #   - Slots 1 (2.5 mm, groove 0.9) and 6 (5.0 mm, groove 3.4) printed
    #     poorly (groove too shallow at slot 1, wall too thin at slot 6)
    # V2 sweep stays within the known-good zone and extends upward to
    # test the upper print-quality limit.
    # 10 slots = 50 deg wedge sector (was 30 deg for the V1 6-slot wedge).
    (1.22, 3.50, 1.90),
    (1.22, 3.70, 2.10),
    (1.22, 3.90, 2.30),
    (1.22, 4.10, 2.50),
    (1.22, 4.30, 2.70),
    (1.22, 4.50, 2.90),    # <-- matches V1 known-good slot 5
    (1.22, 4.70, 3.10),
    (1.22, 4.90, 3.30),
    (1.22, 5.10, 3.50),    # print-risk: deep groove
    (1.22, 5.30, 3.70),    # print-risk: thin wall in spring-groove zone
]

# Derived
CYL_OUTER_R   = CYL_OD / 2.0
CYL_INNER_R   = CYL_ID / 2.0
SLOT_PITCH_DEG = 360.0 / SLOT_COUNT          # 5.0
SLOT_PITCH_MM  = math.pi * CYL_OD / SLOT_COUNT  # 4.987
WALL_BETWEEN   = SLOT_PITCH_MM - SLOT_WIDTH     # 3.77
WALL_THICKNESS = (CYL_OD - CYL_ID) / 2.0        # 13.15

# =============================================================================
# STARTUP REPORT
# =============================================================================
print("=" * 70)
print("CSM V3 - CYLINDER V3.0  (Erlbacher-pattern, full-height slots)")
print("=" * 70)
print(f"OD x ID x H:        {CYL_OD} x {CYL_ID} x {CYL_HEIGHT} mm")
print(f"Wall thickness:     {WALL_THICKNESS:.2f} mm")
print(f"Slots:              {SLOT_COUNT} x ({SLOT_WIDTH} W x {SLOT_DEPTH} D x {CYL_HEIGHT} H) mm")
print(f"Slot pitch:         {SLOT_PITCH_DEG} deg  /  {SLOT_PITCH_MM:.3f} mm arc")
print(f"Wall between fins:  {WALL_BETWEEN:.2f} mm")
print(f"Stepped slot zones (Erlbacher / tru-knit pattern):")
print(f"  Body (Z=0 to {CYL_HEIGHT - TOP_ZONE_HEIGHT - TOP_TRANSITION_H:.1f}mm):  "
      f"NARROW {SLOT_WIDTH}mm  -- grips needle stem")
print(f"  Transition ({CYL_HEIGHT - TOP_ZONE_HEIGHT - TOP_TRANSITION_H:.1f}-"
      f"{CYL_HEIGHT - TOP_ZONE_HEIGHT:.1f}mm):    smooth chamfer "
      f"{SLOT_WIDTH}mm -> {TOP_ZONE_WIDTH}mm")
print(f"  Top zone ({CYL_HEIGHT - TOP_ZONE_HEIGHT:.1f}-{CYL_HEIGHT}mm):       "
      f"WIDE {TOP_ZONE_WIDTH}mm   -- yarn/hook/latch clearance, no needle grip")
print(f"Spring groove:      Z={SPRING_GROOVE_Z_BOT:.1f}-{SPRING_GROOVE_Z_TOP:.1f}mm "
      f"({SPRING_GROOVE_W}W x {SPRING_GROOVE_DEPTH}D)")
print(f"Spring wire 2.79mm in {SPRING_GROOVE_DEPTH}mm-deep groove -> "
      f"{2.79 - SPRING_GROOVE_DEPTH:.2f}mm protrusion past OD")
print(f"Bottom ring:        {BOTTOM_THICK}mm thick annular ring")
print(f"                    Central D{TAKEDOWN_OPEN_D}mm opening for sock take-down + weight")
print(f"                    Solid annulus from radius {TAKEDOWN_OPEN_D/2:.1f}mm to "
      f"{CYL_OUTER_R - SLOT_DEPTH:.2f}mm carries 4x bolt pockets")
print(f"Slot root fillet:   R{SLOT_ROOT_FILLET}mm at slot-bottom internal corners")
print(f"                    (CRITICAL: PETG fatigue prevention under cam load)")
print(f"Top edge:           {TOP_EDGE_CHAMFER}mm chamfer (simple, OCC-stable)")
print(f"Bottom edge:        {BOT_EDGE_CHAMFER}mm chamfer (edge-break only)")
print(f"Magnet pocket:      D{MAGNET_POCKET_D} x {MAGNET_POCKET_H}mm at PCD "
      f"{MAGNET_PCD}mm, {MAGNET_ANGLE_DEG} deg (one-pulse-per-rev index)")
print(f"Hub pocket:         D{HUB_POCKET_D} x {HUB_POCKET_H}mm  (receives drive hub D18 boss)")
print(f"Heat-set inserts:   {BOLT_COUNT} x M5 inserts at PCD {BOLT_PCD}mm, "
      f"offset {BOLT_ANGLE_OFF} deg  (matches drive hub V2.4.2)")
print(f"Insert pocket:      D{INSERT_HOLE_D} x {INSERT_HOLE_H}mm deep "
      f"(for B0DPQJ4W3Z M5 brass inserts)")
print(f"Mount method:       4x M5 flathead bolts UP from below drive hub flange")
print(f"                    into M5 heat-set inserts at cylinder bottom")
print()
print("CAM RING V6.5 COMPATIBILITY:")
print(f"  OD={CYL_OD}mm vs cam ring ID=115mm -> 0.35mm/side clearance  OK")
print(f"  Butts travel Z=19-31mm freely in uniform slot               OK")
print()

# =============================================================================
# BUILD CYLINDER
# =============================================================================
doc = FreeCAD.newDocument("CSM_Cylinder_V3_0")

print("[1/6] Building stepped-bore cylinder (D50 take-down + D88 main bore)...")
outer = Part.makeCylinder(CYL_OUTER_R, CYL_HEIGHT)
# Main bore D88: from Z=BOTTOM_THICK up to top (full sock-collection region)
inner_upper = Part.makeCylinder(CYL_INNER_R, CYL_HEIGHT - BOTTOM_THICK + 2.0)
inner_upper.translate(FreeCAD.Vector(0, 0, BOTTOM_THICK))
# Take-down opening D50 through the bottom ring (Z=0 to BOTTOM_THICK)
inner_lower = Part.makeCylinder(TAKEDOWN_OPEN_D / 2.0, BOTTOM_THICK + 2.0)
inner_lower.translate(FreeCAD.Vector(0, 0, -1.0))
body = outer.cut(inner_upper).cut(inner_lower)

print("[2/6] Cutting hub pocket + bolt holes...")
pocket = Part.makeCylinder(HUB_POCKET_D / 2.0, HUB_POCKET_H + 0.1)
pocket.translate(FreeCAD.Vector(0, 0, -0.05))
body = body.cut(pocket)

if HUB_POCKET_CHAM > 0:
    cone = Part.makeCone(
        HUB_POCKET_D / 2.0 + HUB_POCKET_CHAM,
        HUB_POCKET_D / 2.0,
        HUB_POCKET_CHAM,
    )
    cone.translate(FreeCAD.Vector(0, 0, -0.001))
    body = body.cut(cone)

# 4x BLIND holes for M5 heat-set inserts, opening at the bottom face.
# Drive hub bolts come up from below, thread into the inserts.
# 45 deg angular offset matches drive hub V2.4.2 -- holes line up exactly.
for i in range(BOLT_COUNT):
    ang = math.radians(i * (360.0 / BOLT_COUNT) + BOLT_ANGLE_OFF)
    bx = (BOLT_PCD / 2.0) * math.cos(ang)
    by = (BOLT_PCD / 2.0) * math.sin(ang)
    pocket = Part.makeCylinder(INSERT_HOLE_D / 2.0, INSERT_HOLE_H + 0.1)
    pocket.translate(FreeCAD.Vector(bx, by, -0.05))   # open at bottom face
    body = body.cut(pocket)

# Hall sensor magnet pocket (one pulse per revolution, bottom face)
mag_ang = math.radians(MAGNET_ANGLE_DEG)
mx = (MAGNET_PCD / 2.0) * math.cos(mag_ang)
my = (MAGNET_PCD / 2.0) * math.sin(mag_ang)
mag_pocket = Part.makeCylinder(MAGNET_POCKET_D / 2.0, MAGNET_POCKET_H + 0.1)
mag_pocket.translate(FreeCAD.Vector(mx, my, -0.05))
body = body.cut(mag_pocket)
print(f"  Magnet pocket at PCD {MAGNET_PCD}mm, {MAGNET_ANGLE_DEG} deg, "
      f"D{MAGNET_POCKET_D} x {MAGNET_POCKET_H}mm")

print("[3/6] Building 72 slot cutters: uniform depth, body+transition+wide top...")
# Each slot has two parts:
#   (1) main body  = uniform rectangular channel, full cylinder height
#   (2) top flare  = lofted wedge that widens the slot near the top
#                     This creates the curved profile on each fin top
#                     visible in the Erlbacher photo.
sx_inner = CYL_OUTER_R - SLOT_DEPTH
sx_outer = CYL_OUTER_R + 1.0  # +1mm safety past OD for clean boolean

def build_slot_cutter(body_w, angle_deg, slot_d=None):
    """
    Build a three-section slot cutter:
      [0]  Body zone     -- narrow (body_w), grips needle stem
      [1]  Transition    -- smooth chamfer from narrow body to wide top
      [2]  Top zone      -- wide (TOP_ZONE_WIDTH), yarn/hook clearance
    Radial DEPTH = slot_d (defaults to global SLOT_DEPTH; wedge varies it).
    Body box gets its TWO INNER vertical edges filleted before fusing.
    Those become the slot-bottom internal corners -- without rounding
    here, PETG fatigue cracks initiate at those exact edges under cam
    load. This is the most important structural fix in V3.0.
    """
    d = SLOT_DEPTH if slot_d is None else slot_d
    sx_inner_local = CYL_OUTER_R - d
    # SLOT STARTS AT TOP OF BOTTOM RING (Z=BOTTOM_THICK), NOT AT Z=0.
    # This keeps the bottom ring as a SOLID continuous annulus -- no slot
    # interruptions through the mounting zone. Matches the reference cylinder
    # design philosophy and strengthens the print at the bolt-load region.
    # Needles now insert from the TOP (through the wider top zone, then slide
    # down) instead of from the bottom.
    z_slot_bot  = BOTTOM_THICK              # slot floor sits on top of ring
    z_body_top  = CYL_HEIGHT - TOP_ZONE_HEIGHT - TOP_TRANSITION_H
    z_trans_top = CYL_HEIGHT - TOP_ZONE_HEIGHT

    # ---- (1) Body zone: narrow slot, from z_slot_bot to z_body_top ----
    body_height = z_body_top - z_slot_bot
    body = Part.makeBox(
        sx_outer - sx_inner_local,
        body_w,
        body_height + 0.1,
    )
    body.translate(FreeCAD.Vector(sx_inner_local, -body_w / 2.0, z_slot_bot))

    # Fillet the 2 vertical edges on the inner-most face (slot bottom corners)
    if SLOT_ROOT_FILLET > 0:
        root_edges = []
        for e in body.Edges:
            v1 = e.Vertexes[0].Point
            v2 = e.Vertexes[1].Point
            # Vertical edges on the inner-most face (x = sx_inner_local)
            if (abs(v1.x - sx_inner_local) < 0.01 and
                abs(v2.x - sx_inner_local) < 0.01 and
                abs(v1.z - v2.z) > 0.5):       # significant vertical extent
                root_edges.append(e)
        if root_edges:
            try:
                body = body.makeFillet(SLOT_ROOT_FILLET, root_edges)
            except Exception as ex_rf:
                # Sharp corners better than failed boolean -- keep going
                print(f"    root fillet skipped at {angle_deg:.1f} deg: {ex_rf}")

    # ---- (2) Transition: lofted taper from body_w to TOP_ZONE_WIDTH ----
    pts_bot = [
        FreeCAD.Vector(sx_inner_local, -body_w / 2.0, z_body_top),
        FreeCAD.Vector(sx_outer, -body_w / 2.0, z_body_top),
        FreeCAD.Vector(sx_outer,  body_w / 2.0, z_body_top),
        FreeCAD.Vector(sx_inner_local,  body_w / 2.0, z_body_top),
        FreeCAD.Vector(sx_inner_local, -body_w / 2.0, z_body_top),
    ]
    pts_top = [
        FreeCAD.Vector(sx_inner_local, -TOP_ZONE_WIDTH / 2.0, z_trans_top),
        FreeCAD.Vector(sx_outer, -TOP_ZONE_WIDTH / 2.0, z_trans_top),
        FreeCAD.Vector(sx_outer,  TOP_ZONE_WIDTH / 2.0, z_trans_top),
        FreeCAD.Vector(sx_inner_local,  TOP_ZONE_WIDTH / 2.0, z_trans_top),
        FreeCAD.Vector(sx_inner_local, -TOP_ZONE_WIDTH / 2.0, z_trans_top),
    ]
    bot_wire = Part.makePolygon(pts_bot)
    top_wire = Part.makePolygon(pts_top)
    transition = Part.makeLoft([bot_wire, top_wire], True)

    # ---- (3a) Top zone main: TOP_ZONE_WIDTH from z_trans_top to flare bottom
    z_flare_bot = CYL_HEIGHT - FIN_TOP_CHAMFER_H
    z_flare_top = CYL_HEIGHT + 0.5    # +0.5mm safety above cylinder top
    top = Part.makeBox(
        sx_outer - sx_inner_local,
        TOP_ZONE_WIDTH,
        z_flare_bot - z_trans_top + 0.1,
    )
    top.translate(FreeCAD.Vector(sx_inner_local, -TOP_ZONE_WIDTH / 2.0, z_trans_top))

    # ---- (3b) Flare cap: lofts from TOP_ZONE_WIDTH at z_flare_bot to
    #           (TOP_ZONE_WIDTH + 2 * FIN_TOP_CHAMFER) at z_flare_top.
    # This is the carved chamfer on every fin top side -- guaranteed visible
    # because it's part of the cutter geometry, not a post-cut operation.
    flare_w_top = TOP_ZONE_WIDTH + 2.0 * FIN_TOP_CHAMFER
    pts_fb = [
        FreeCAD.Vector(sx_inner_local, -TOP_ZONE_WIDTH / 2.0, z_flare_bot),
        FreeCAD.Vector(sx_outer,       -TOP_ZONE_WIDTH / 2.0, z_flare_bot),
        FreeCAD.Vector(sx_outer,        TOP_ZONE_WIDTH / 2.0, z_flare_bot),
        FreeCAD.Vector(sx_inner_local,  TOP_ZONE_WIDTH / 2.0, z_flare_bot),
        FreeCAD.Vector(sx_inner_local, -TOP_ZONE_WIDTH / 2.0, z_flare_bot),
    ]
    pts_ft = [
        FreeCAD.Vector(sx_inner_local, -flare_w_top / 2.0, z_flare_top),
        FreeCAD.Vector(sx_outer,       -flare_w_top / 2.0, z_flare_top),
        FreeCAD.Vector(sx_outer,        flare_w_top / 2.0, z_flare_top),
        FreeCAD.Vector(sx_inner_local,  flare_w_top / 2.0, z_flare_top),
        FreeCAD.Vector(sx_inner_local, -flare_w_top / 2.0, z_flare_top),
    ]
    flare_bot_wire = Part.makePolygon(pts_fb)
    flare_top_wire = Part.makePolygon(pts_ft)
    flare = Part.makeLoft([flare_bot_wire, flare_top_wire], True)

    cutter = body.fuse(transition).fuse(top).fuse(flare)
    cutter.rotate(FreeCAD.Vector(0, 0, 0), FreeCAD.Vector(0, 0, 1), angle_deg)
    return cutter

slot_cutters = []
for i in range(SLOT_COUNT):
    slot_cutters.append(build_slot_cutter(SLOT_WIDTH, i * SLOT_PITCH_DEG))

print("[4/6] Fusing slot cutters and applying boolean cut...")
# Tree-fuse for speed: O(log N) depth instead of O(N)
def tree_fuse(shapes):
    while len(shapes) > 1:
        next_level = []
        for i in range(0, len(shapes), 2):
            if i + 1 < len(shapes):
                next_level.append(shapes[i].fuse(shapes[i + 1]))
            else:
                next_level.append(shapes[i])
        shapes = next_level
    return shapes[0]

master = tree_fuse(slot_cutters)
body = body.cut(master)

print(f"[5/6] Cutting spring groove (Z={SPRING_GROOVE_Z_BOT:.1f}"
      f"-{SPRING_GROOVE_Z_TOP:.1f}, depth={SPRING_GROOVE_DEPTH}mm)...")
g_outer = Part.makeCylinder(
    CYL_OUTER_R + 1.0, SPRING_GROOVE_W,
    FreeCAD.Vector(0, 0, SPRING_GROOVE_Z_BOT),
)
g_inner = Part.makeCylinder(
    CYL_OUTER_R - SPRING_GROOVE_DEPTH, SPRING_GROOVE_W + 0.1,
    FreeCAD.Vector(0, 0, SPRING_GROOVE_Z_BOT - 0.05),
)
groove = g_outer.cut(g_inner)
body = body.cut(groove)

print("[6/6] Radial chamfers (OD top + bore top) + bottom edge...")
# Front-to-back easing on the fin top via cone-based boolean cuts.
# Robust because cones are simple solids.

# --- OD top chamfer: annular wedge cutter (large cyl MINUS tapered cone) ---
try:
    od_outer_cyl = Part.makeCylinder(CYL_OUTER_R + 2.0, OD_TOP_CHAMFER + 0.1)
    od_outer_cyl.translate(FreeCAD.Vector(0, 0, CYL_HEIGHT - OD_TOP_CHAMFER))
    od_inner_cone = Part.makeCone(
        CYL_OUTER_R,                    # bottom radius (= OD)
        CYL_OUTER_R - OD_TOP_CHAMFER,   # top radius (chamfered inward)
        OD_TOP_CHAMFER + 0.2,
    )
    od_inner_cone.translate(FreeCAD.Vector(0, 0, CYL_HEIGHT - OD_TOP_CHAMFER - 0.05))
    od_wedge = od_outer_cyl.cut(od_inner_cone)
    body = body.cut(od_wedge)
    print(f"  OD top chamfered @ {OD_TOP_CHAMFER}mm (annular wedge cut)")
except Exception as ex:
    print(f"  OD top chamfer skipped: {ex}")

# --- Bore top chamfer: simple cone (widens bore at the top) ---
try:
    bore_cone = Part.makeCone(
        CYL_INNER_R,                    # bottom radius (= bore)
        CYL_INNER_R + BORE_TOP_CHAMFER, # top radius (widened)
        BORE_TOP_CHAMFER + 0.1,
    )
    bore_cone.translate(FreeCAD.Vector(0, 0, CYL_HEIGHT - BORE_TOP_CHAMFER))
    body = body.cut(bore_cone)
    print(f"  Bore top chamfered @ {BORE_TOP_CHAMFER}mm (cone cut)")
except Exception as ex:
    print(f"  Bore top chamfer skipped: {ex}")

# --- Bottom OD edge chamfer (post-cut, OD only -- simple geometry) ---
try:
    bot_od_edges = []
    for e in body.Edges:
        v1 = e.Vertexes[0].Point
        v2 = e.Vertexes[1].Point
        if abs(v1.z - v2.z) < 0.01 and abs(v1.z) < 0.05:
            r1 = math.sqrt(v1.x ** 2 + v1.y ** 2)
            if abs(r1 - CYL_OUTER_R) < 0.05:
                bot_od_edges.append(e)
    if bot_od_edges:
        body = body.makeChamfer(BOT_EDGE_CHAMFER, bot_od_edges)
        print(f"  Chamfered {len(bot_od_edges)} OD bottom edges @ {BOT_EDGE_CHAMFER}mm")
except Exception as ex:
    print(f"  Bottom chamfer skipped: {ex}")

# Add the body to the document
obj = doc.addObject("Part::Feature", "Cylinder_V3_0")
obj.Shape = body
if FreeCAD.GuiUp and obj.ViewObject is not None:
    obj.ViewObject.ShapeColor = (0.72, 0.72, 0.74)   # aluminum gray, like Erlbacher
doc.recompute()

vol_mm3 = body.Volume
print(f"\nVolume: {vol_mm3:.0f} mm^3  (~{vol_mm3 * 1.27 / 1000:.0f}g PETG)")

# =============================================================================
# BUILD TEST WEDGES (two 30 deg pie slices with isolated variables)
# =============================================================================
def build_wedge(wedge_slots, x_offset, color, label):
    """Build a 30 deg test wedge with the given list of slot entries.
       Each entry is either:
         (slot_width, slot_depth)                  -- shared global groove
         (slot_width, slot_depth, groove_depth)    -- per-slot angular groove
       Includes test insert + magnet pockets, spring groove, top chamfers."""
    # Normalize: ensure every entry is a (w, d, g_or_None) triple
    norm_slots = []
    per_slot_groove = False
    for entry in wedge_slots:
        if len(entry) == 3:
            norm_slots.append((entry[0], entry[1], entry[2]))
            per_slot_groove = True
        else:
            norm_slots.append((entry[0], entry[1], None))

    print()
    print(f"[{label}] Building 30 deg test wedge:")
    for i, (sw, sd, gd) in enumerate(norm_slots):
        if gd is None:
            print(f"        Slot {i+1}: width={sw}mm  depth={sd}mm  (shared groove)")
        else:
            preload = (gd + 1.8) - sd
            print(f"        Slot {i+1}: width={sw}mm  depth={sd}mm  "
                  f"groove={gd}mm  -> spring preload {preload:+.2f}mm")

    w_outer = Part.makeCylinder(CYL_OUTER_R, CYL_HEIGHT)
    w_inner_up = Part.makeCylinder(CYL_INNER_R, CYL_HEIGHT - BOTTOM_THICK + 2.0)
    w_inner_up.translate(FreeCAD.Vector(0, 0, BOTTOM_THICK))
    w_inner_lo = Part.makeCylinder(TAKEDOWN_OPEN_D / 2.0, BOTTOM_THICK + 2.0)
    w_inner_lo.translate(FreeCAD.Vector(0, 0, -1.0))
    wb = w_outer.cut(w_inner_up).cut(w_inner_lo)

    # Auto-derive wedge angle from slot count.  Each slot occupies
    # SLOT_PITCH_DEG (5 deg).  6 slots -> 30 deg.  10 slots -> 50 deg.
    wedge_angle_deg = len(norm_slots) * SLOT_PITCH_DEG

    # Keep only the sector
    sector = Part.makeCylinder(
        CYL_OUTER_R + 5.0, CYL_HEIGHT + 2.0,
        FreeCAD.Vector(0, 0, -1.0),
        FreeCAD.Vector(0, 0, 1.0),
        wedge_angle_deg,
    )
    wb = wb.common(sector)

    # Slot cuts
    wedge_cutters = []
    slot_angles = []   # (center_angle_deg) per slot -- for per-slot groove segs
    for i, (sw, sd, _gd) in enumerate(norm_slots):
        angle = (i + 0.5) * SLOT_PITCH_DEG
        slot_angles.append(angle)
        wedge_cutters.append(build_slot_cutter(sw, angle, slot_d=sd))
    wb = wb.cut(tree_fuse(wedge_cutters))

    # Insert pocket test (10 deg) + magnet pocket test (20 deg)
    test_ang_i = math.radians(10.0)
    tb_ix = (BOLT_PCD / 2.0) * math.cos(test_ang_i)
    tb_iy = (BOLT_PCD / 2.0) * math.sin(test_ang_i)
    tp_i = Part.makeCylinder(INSERT_HOLE_D / 2.0, INSERT_HOLE_H + 0.1)
    tp_i.translate(FreeCAD.Vector(tb_ix, tb_iy, -0.05))
    wb = wb.cut(tp_i)

    test_ang_m = math.radians(20.0)
    tb_mx = (MAGNET_PCD / 2.0) * math.cos(test_ang_m)
    tb_my = (MAGNET_PCD / 2.0) * math.sin(test_ang_m)
    tp_m = Part.makeCylinder(MAGNET_POCKET_D / 2.0, MAGNET_POCKET_H + 0.1)
    tp_m.translate(FreeCAD.Vector(tb_mx, tb_my, -0.05))
    wb = wb.cut(tp_m)

    if per_slot_groove:
        # Per-slot angular groove segments: each slot owns a SLOT_PITCH_DEG
        # angular slice of the spring groove at its own groove depth. The
        # spring (when installed across the wedge) bears differently on each
        # slot's needle depending on that slot's groove depth.
        groove_segs = []
        for i, (_sw, _sd, gd) in enumerate(norm_slots):
            seg_start = i * SLOT_PITCH_DEG
            seg_outer = Part.makeCylinder(
                CYL_OUTER_R + 1.0, SPRING_GROOVE_W,
                FreeCAD.Vector(0, 0, SPRING_GROOVE_Z_BOT),
                FreeCAD.Vector(0, 0, 1.0),
                SLOT_PITCH_DEG,
            )
            seg_inner = Part.makeCylinder(
                CYL_OUTER_R - gd, SPRING_GROOVE_W + 0.1,
                FreeCAD.Vector(0, 0, SPRING_GROOVE_Z_BOT - 0.05),
                FreeCAD.Vector(0, 0, 1.0),
                SLOT_PITCH_DEG,
            )
            seg = seg_outer.cut(seg_inner)
            seg.rotate(FreeCAD.Vector(0, 0, 0), FreeCAD.Vector(0, 0, 1), seg_start)
            groove_segs.append(seg)
        wb = wb.cut(tree_fuse(groove_segs))
    else:
        # Shared groove across the whole wedge sector (used by WEDGE A)
        wg_outer = Part.makeCylinder(
            CYL_OUTER_R + 1.0, SPRING_GROOVE_W,
            FreeCAD.Vector(0, 0, SPRING_GROOVE_Z_BOT),
        )
        wg_inner = Part.makeCylinder(
            CYL_OUTER_R - SPRING_GROOVE_DEPTH, SPRING_GROOVE_W + 0.1,
            FreeCAD.Vector(0, 0, SPRING_GROOVE_Z_BOT - 0.05),
        )
        wg_cutter = wg_outer.cut(wg_inner)
        wg_sector = Part.makeCylinder(
            CYL_OUTER_R + 5.0, CYL_HEIGHT + 2.0,
            FreeCAD.Vector(0, 0, -1.0),
            FreeCAD.Vector(0, 0, 1.0),
            wedge_angle_deg,
        )
        wb = wb.cut(wg_cutter.common(wg_sector))

    # OD top + bore top chamfers
    try:
        w_od_outer = Part.makeCylinder(CYL_OUTER_R + 2.0, OD_TOP_CHAMFER + 0.1)
        w_od_outer.translate(FreeCAD.Vector(0, 0, CYL_HEIGHT - OD_TOP_CHAMFER))
        w_od_inner = Part.makeCone(
            CYL_OUTER_R, CYL_OUTER_R - OD_TOP_CHAMFER, OD_TOP_CHAMFER + 0.2,
        )
        w_od_inner.translate(FreeCAD.Vector(0, 0, CYL_HEIGHT - OD_TOP_CHAMFER - 0.05))
        wb = wb.cut(w_od_outer.cut(w_od_inner))
        w_bore_cone = Part.makeCone(
            CYL_INNER_R, CYL_INNER_R + BORE_TOP_CHAMFER, BORE_TOP_CHAMFER + 0.1,
        )
        w_bore_cone.translate(FreeCAD.Vector(0, 0, CYL_HEIGHT - BORE_TOP_CHAMFER))
        wb = wb.cut(w_bore_cone)
    except Exception as ex:
        print(f"        Top chamfers skipped: {ex}")

    # Offset for side-by-side display
    wb.translate(FreeCAD.Vector(x_offset, 0, 0))
    return wb

wedge_A = build_wedge(WEDGE_A_SLOTS, x_offset=150.0, color=(0.85, 0.55, 0.25), label="WEDGE A (width)")
wedge_B = build_wedge(WEDGE_B_SLOTS, x_offset=250.0, color=(0.55, 0.85, 0.45), label="WEDGE B (depth)")

obj_wedge_A = doc.addObject("Part::Feature", "Cylinder_V3_0_WEDGE_A_WIDTH")
obj_wedge_A.Shape = wedge_A
if FreeCAD.GuiUp and obj_wedge_A.ViewObject is not None:
    obj_wedge_A.ViewObject.ShapeColor = (0.85, 0.55, 0.25)

obj_wedge_B = doc.addObject("Part::Feature", "Cylinder_V3_0_WEDGE_B_DEPTH")
obj_wedge_B.Shape = wedge_B
if FreeCAD.GuiUp and obj_wedge_B.ViewObject is not None:
    obj_wedge_B.ViewObject.ShapeColor = (0.55, 0.85, 0.45)
doc.recompute()

print(f"        Wedge A volume: {wedge_A.Volume:.0f} mm^3  (~{wedge_A.Volume * 1.27 / 1000:.0f}g PETG)")
print(f"        Wedge B volume: {wedge_B.Volume:.0f} mm^3  (~{wedge_B.Volume * 1.27 / 1000:.0f}g PETG)")
print(f"        Print time each: ~30-45 min")

# =============================================================================
# EXPORT
# =============================================================================
print("\nExporting STL (full cylinder)...")
try:
    tmp = doc.addObject("Part::Feature", "_tmp_export")
    tmp.Shape = body.copy()
    Part.export([tmp], PATH_STL)
    doc.removeObject("_tmp_export")
    print(f"  [OK] {PATH_STL}")
except Exception as ex:
    print(f"  STL error: {ex}")

print("\nExporting STL (test wedges -- both translated back to origin)...")
for wb_obj, x_off, path, name in [
    (wedge_A, 150.0, PATH_STL_WEDGE_A, "_tmp_wedge_A"),
    (wedge_B, 250.0, PATH_STL_WEDGE_B, "_tmp_wedge_B"),
]:
    try:
        export_shape = wb_obj.copy()
        export_shape.translate(FreeCAD.Vector(-x_off, 0, 0))
        tmp = doc.addObject("Part::Feature", name)
        tmp.Shape = export_shape
        Part.export([tmp], path)
        doc.removeObject(name)
        print(f"  [OK] {path}")
    except Exception as ex:
        print(f"  Wedge STL error: {ex}")

print("\nExporting PNG renders...")
png_ok = False
try:
    import FreeCADGui
    if FreeCAD.GuiUp:
        gdoc = FreeCADGui.getDocument(doc.Name)
        view = gdoc.activeView()
        W, H, BG = 1920, 1080, "White"
        # Full cylinder views
        obj.ViewObject.Visibility = True
        obj_wedge_A.ViewObject.Visibility = False
        view.viewIsometric(); view.fitAll()
        view.saveImage(PATH_PNG_ISO, W, H, BG); print(f"  [OK] {PATH_PNG_ISO}")
        view.viewTop(); view.fitAll()
        view.saveImage(PATH_PNG_TOP, W, H, BG); print(f"  [OK] {PATH_PNG_TOP}")
        view.viewFront(); view.fitAll()
        view.saveImage(PATH_PNG_FRONT, W, H, BG); print(f"  [OK] {PATH_PNG_FRONT}")

        # Test wedge view
        obj.ViewObject.Visibility = False
        obj_wedge_A.ViewObject.Visibility = True
        view.viewIsometric(); view.fitAll()
        view.saveImage(PATH_PNG_WEDGE, W, H, BG); print(f"  [OK] {PATH_PNG_WEDGE}")

        # Restore both visible
        obj.ViewObject.Visibility = True
        obj_wedge_A.ViewObject.Visibility = True
        view.viewIsometric(); view.fitAll()
        png_ok = True
    else:
        print("  [SKIP] No GUI -- run from FreeCAD GUI to generate PNGs")
except Exception as ex:
    print(f"  PNG error: {ex}")

# =============================================================================
# SVG BLUEPRINT
# =============================================================================
print("\nExporting SVG blueprint...")
SCALE = 1.6  # mm -> px for top view

def _circ(r, fill="none", stroke="#1e3a5f", sw=1.2, dash=""):
    da = f' stroke-dasharray="{dash}"' if dash else ""
    return (f'<circle cx="0" cy="0" r="{r * SCALE:.2f}" fill="{fill}" '
            f'stroke="{stroke}" stroke-width="{sw}"{da}/>')

slot_lines = ""
for i in range(SLOT_COUNT):
    ang = math.radians(i * SLOT_PITCH_DEG)
    r_out = CYL_OUTER_R * SCALE
    r_in = (CYL_OUTER_R - SLOT_DEPTH) * SCALE
    x1, y1 = r_out * math.cos(ang), r_out * math.sin(ang)
    x2, y2 = r_in * math.cos(ang), r_in * math.sin(ang)
    slot_lines += (f'<line x1="{x1:.2f}" y1="{y1:.2f}" '
                   f'x2="{x2:.2f}" y2="{y2:.2f}" '
                   f'stroke="#c0392b" stroke-width="0.6"/>\n')

bolt_marks = ""
for i in range(BOLT_COUNT):
    ang = math.radians(i * 90.0 + BOLT_ANGLE_OFF)
    br = (BOLT_PCD / 2.0) * SCALE
    bx, by = br * math.cos(ang), br * math.sin(ang)
    bolt_marks += (f'<circle cx="{bx:.2f}" cy="{by:.2f}" '
                   f'r="{INSERT_HOLE_D / 2 * SCALE:.2f}" '
                   f'fill="#ffeacc" stroke="#27ae60" stroke-width="1"/>\n')

# Side section
H_SCALE = 3.0
sv_x, sv_w = 600, 120

def _sv_rect(z_bot, z_top, label="", col="#d4e1ed", scol="#1e3a5f", sw=1.0):
    y_top = 60 + (CYL_HEIGHT - z_top) * H_SCALE
    y_bot = 60 + (CYL_HEIGHT - z_bot) * H_SCALE
    h = y_bot - y_top
    rect = (f'<rect x="{sv_x}" y="{y_top:.1f}" width="{sv_w}" '
            f'height="{h:.1f}" fill="{col}" stroke="{scol}" stroke-width="{sw}"/>\n')
    if label:
        rect += (f'<text x="{sv_x + sv_w/2:.0f}" y="{y_top + h/2 + 4:.1f}" '
                 f'text-anchor="middle" font-size="9" fill="#333">{label}</text>\n')
    return rect

svg = f'''<?xml version="1.0" encoding="UTF-8"?>
<svg xmlns="http://www.w3.org/2000/svg" width="950" height="700"
     font-family="Arial, sans-serif">
  <rect width="950" height="700" fill="#fafafa"/>
  <text x="475" y="28" text-anchor="middle" font-size="17"
        font-weight="bold" fill="#1e3a5f">
    CSM V3 -- Cylinder V3.0 (Erlbacher-pattern, uniform-depth slots with top flare)
  </text>
  <text x="475" y="46" text-anchor="middle" font-size="11" fill="#555">
    OD {CYL_OD}mm . ID {CYL_ID}mm . H {CYL_HEIGHT}mm . {SLOT_COUNT} slots . 12-gauge . PETG
  </text>

  <text x="200" y="76" text-anchor="middle" font-size="12"
        font-weight="bold" fill="#1e3a5f">Top View</text>
  <g transform="translate(200, 360)">
    {_circ(CYL_OUTER_R, fill="#d4e1ed")}
    {_circ(CYL_ID / 2, fill="#fafafa", stroke="#888", sw=0.8)}
    {_circ(HUB_POCKET_D / 2, fill="#ffe8a0", stroke="#b8860b", sw=0.8)}
    {slot_lines}
    {_circ(BOLT_PCD / 2, fill="none", stroke="#27ae60", sw=0.5, dash="3 2")}
    {bolt_marks}
    {_circ(CYL_OUTER_R - SPRING_GROOVE_DEPTH, fill="none",
           stroke="#8e44ad", sw=0.8, dash="4 3")}
  </g>

  <text x="{sv_x + sv_w/2:.0f}" y="76" text-anchor="middle"
        font-size="12" font-weight="bold" fill="#1e3a5f">Side Section (to scale)</text>
  {_sv_rect(0, CYL_HEIGHT, col="#d4e1ed")}
  <rect x="{sv_x + 8}" y="60" width="{sv_w - 16}"
        height="{CYL_HEIGHT * H_SCALE:.1f}" fill="white" stroke="none"/>
  {_sv_rect(0, CYL_HEIGHT, label="Full-height slot zone", col="#e8f0fb", scol="#5d8fcd")}
  {_sv_rect(SPRING_GROOVE_Z_BOT, SPRING_GROOVE_Z_TOP, label="Spring groove",
            col="#d8b4fe", scol="#8e44ad", sw=1.5)}
  {_sv_rect(19, 31, label="Cam ring engagement", col="#fed7aa",
            scol="#d97706", sw=1.0)}
  {_sv_rect(0, HUB_POCKET_H, label="Hub pocket", col="#ffe8a0", scol="#b8860b")}

  <rect x="30" y="590" width="890" height="100" fill="#fff" stroke="#ccc" rx="4"/>
  <text x="475" y="609" text-anchor="middle" font-size="11"
        font-weight="bold" fill="#1e3a5f">Critical Dimensions</text>
  <g font-size="10" fill="#333">
    <text x="50"  y="627">OD: {CYL_OD}mm (Legare 4.5")</text>
    <text x="220" y="627">ID: {CYL_ID}mm</text>
    <text x="340" y="627">H: {CYL_HEIGHT}mm</text>
    <text x="440" y="627">Wall: {WALL_THICKNESS:.2f}mm</text>
    <text x="560" y="627">Slots: {SLOT_COUNT} @ {SLOT_PITCH_DEG} deg</text>
    <text x="720" y="627">Pitch: {SLOT_PITCH_MM:.3f}mm</text>

    <text x="50"  y="645">Slot W x D: {SLOT_WIDTH} x {SLOT_DEPTH}mm (uniform full height)</text>
    <text x="340" y="645">Root fillet: R{SLOT_ROOT_FILLET}mm</text>
    <text x="440" y="645">Wall btw: {WALL_BETWEEN:.2f}mm</text>
    <text x="560" y="645">Spring: Z={SPRING_GROOVE_Z_BOT:.1f}-{SPRING_GROOVE_Z_TOP:.1f}mm</text>

    <text x="50"  y="663">Hub pocket: D{HUB_POCKET_D} x {HUB_POCKET_H}mm</text>
    <text x="240" y="663">M5 inserts: {BOLT_COUNT} x PCD {BOLT_PCD:.0f}mm @ 45 deg offset</text>
    <text x="500" y="663">Insert pocket: D{INSERT_HOLE_D} x {INSERT_HOLE_H}mm</text>
    <text x="720" y="663">Top chamfer {TOP_EDGE_CHAMFER} / Bot {BOT_EDGE_CHAMFER}</text>

    <text x="50"  y="681" font-style="italic" fill="#666">
      Slots have uniform radial depth full height; circumferential width
      Needle butt rides freely inside slot through full 8mm cam lift.
    </text>
  </g>
</svg>
'''

with open(PATH_SVG, "w", encoding="utf-8") as f:
    f.write(svg)
print(f"  [OK] {PATH_SVG}")

# =============================================================================
# FINAL SUMMARY
# =============================================================================
print()
print("=" * 70)
print("CYLINDER V3.0 -- COMPLETE")
print("=" * 70)
print()
print("WHY THIS MATCHES THE ERLBACHER CYLINDER:")
print(f"  - OD = {CYL_OD}mm  (Legare 4.5\" standard, fits all accessories)")
print(f"  - Hollow tube, no outer flange, no shells")
print(f"  - {SLOT_COUNT} UNIFORM full-height slots ({SLOT_WIDTH}mm x {SLOT_DEPTH}mm x {CYL_HEIGHT}mm)")
print(f"  - Spring groove at Z={SPRING_GROOVE_Z_CTR:.0f}mm (matches photo mid-upper band)")
print(f"  - Cam ring V6.5 engages butts Z=19-31 inside slot -- no obstruction")
print()
print("PRINT SETTINGS:")
print("  Material:      PETG (dry filament)")
print("  Layer height:  0.16mm")
print("  Walls:         5")
print("  Top/bottom:    6 layers")
print("  Infill:        40% Gyroid")
print("  Orientation:   UPRIGHT (Z axis vertical) -- NO supports")
print("  Wall speed:    25 mm/s")
print("  Time:          ~4-6 hours / ~120g PETG")
print()
print("PRINT ORDER (proper experimental design -- print BOTH wedges first):")
print()
print("  WEDGE A (WIDTH sweep, depth fixed at 3.0mm):")
print("    File: CSM_V3_Cylinder_V3_0_WEDGE_A_WIDTH.stl")
for i, entry in enumerate(WEDGE_A_SLOTS):
    w, d = entry[0], entry[1]
    tag = "  <-- baseline" if abs(w - SLOT_WIDTH) < 0.001 else ""
    print(f"      Slot {i+1}:  W={w}mm  D={d}mm{tag}")
print()
print("  WEDGE B (coupled DEPTH + GROOVE sweep, width fixed at 1.22mm):")
print("    File: CSM_V3_Cylinder_V3_0_WEDGE_B_DEPTH.stl")
for i, entry in enumerate(WEDGE_B_SLOTS):
    w, d = entry[0], entry[1]
    g = entry[2] if len(entry) > 2 else None
    tag = "  <-- baseline" if abs(d - SLOT_DEPTH) < 0.001 else ""
    if abs(d - 2.5) < 0.001:
        tag += "  <-- reference STL depth"
    if g is None:
        print(f"      Slot {i+1}:  W={w}mm  D={d}mm{tag}")
    else:
        preload = (g + 1.8) - d
        print(f"      Slot {i+1}:  W={w}mm  D={d}mm  groove={g}mm  "
              f"preload {preload:+.2f}mm{tag}")
print()
print("  HOW TO TEST EACH WEDGE:")
print("    1. Insert a 12g FlyDesigns needle into each of the 6 slots")
print("    2. Slide top-to-bottom; pick the slot where the needle:")
print("       - Slides smoothly with no rattle")
print("       - Cannot wiggle side-to-side")
print("       - Apply lateral force on butt -- fin should not flex visibly")
print("    3. WEDGE A tells you the right WIDTH (best lateral grip)")
print("    4. WEDGE B tells you the right DEPTH (best fin stiffness)")
print()
print("     Also check: insert pocket (M5 brass insert fits cleanly?)")
print("                 magnet pocket (D6 magnet press-fit?)")
print()
print("  Then update SLOT_WIDTH + SLOT_DEPTH in macro, re-run, print full")
print()
print("AFTER FULL PRINT:")
print("  1. Sand slot walls 400 -> 1000 grit")
print("  2. PTFE dry lube on slot walls")
print("  3. Press 4x M5 brass heat-set inserts (B0DPQJ4W3Z) into bottom pockets")
print("     using soldering iron at ~220 C, square to the face")
print("  4. Insert needles from BOTTOM, slide up until butt clears slot bottom")
print("  5. Install spring in groove (wrap around, ends in slot pair)")
print("  6. Set cylinder onto Drive Hub V2.4.2: D18 boss enters D18.2 pocket")
print("  7. From below the drive hub flange, install 4x M5 flathead bolts")
print("     UP through hub countersinks, thread into cylinder heat-set inserts")
print("  8. Torque diagonally in 2-3 passes, ~3 Nm final")
print()
print("FILES:")
print(f"  STL FULL:    {PATH_STL}")
print(f"  STL WEDGE A: {PATH_STL_WEDGE_A}")
print(f"  STL WEDGE B: {PATH_STL_WEDGE_B}")
print(f"  PNGs:        {os.path.dirname(PATH_PNG_ISO)}")
print(f"  SVG:         {PATH_SVG}")
print("=" * 70)
