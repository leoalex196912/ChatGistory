# -*- coding: utf-8 -*-
# =============================================================================
# CSM V3 -- MODULE 10 HMI -- TOUCHSCREEN FRAME V1.0 (Part M10-P05)
# =============================================================================
# Back plate that mounts the ELECROW RC070S 7" HDMI touchscreen
# (Amazon B08FMNDDSL, 165 x 100 x 10 mm, 236 g) to the Cross Beam V1.2
# FRONT face.
#
# Mounting flow:
#   1. ELECROW kit: 4 brass pillars thread INTO the screen back
#   2. M2.5 screws pass THROUGH the frame plate INTO the pillars
#   3. The pillar height holds the screen ~5-8 mm off the frame front
#      face -- HDMI / USB / 3.5 mm jacks all live in that gap
#   4. Cables exit through the bottom-edge cutout, route up the rear
#      mast face, into the beam cable channel, to the Pi
#
# Frame interface to beam:
#   4 of the 6 M5 heat-set inserts on the beam FRONT (-Y) face are used
#   (the outer pair + the next-in pair, at X = +/-55 and +/-33 mm).
#   M5 socket-head bolts go through the frame's top TAB BAND into the
#   beam inserts.
#
# Why elongated slots for screen mounting:
#   ELECROW does not publish the RC070S back-panel PCD.  The 4 slots
#   (20 x 10 mm) cover a generous adjustment range so any reasonable
#   4-corner pattern fits without re-drilling.  Once the first install
#   verifies the actual PCD, V1.1 can fix the holes to size.
#
# Local frame:
#   X = along beam width (and across screen long-axis)
#   Y = thickness (+Y = beam side, -Y = operator side)
#   Z = vertical (Z=0 = bottom edge, Z=FRAME_H = top edge)
# =============================================================================

import FreeCAD, Part, math, os, sys
sys.path.insert(0, r"C:\3D-Project\00_PROJECT_OVERVIEW")
import machine_datums as MD

# ============================================================
# PART METADATA (CSM V3 macro standard header)
# ============================================================
PART_NUMBER     = "M10-P05"
PART_NAME       = "Touchscreen Frame"
VERSION         = "V1.2"
STATUS          = "RC1"
PART_ID         = "CSM_V3_TouchscreenFrame_V1_2"
PRINT_QTY       = 1
PRINT_MATERIAL  = "PETG (PA12 production)"
PRINT_INFILL    = "100%"
PRINT_LAYER     = "0.20 mm"
PRINT_WALLS     = 4

# ============================================================
# Helpers
# ============================================================
def cut_box(shape, w, d, h, origin):
    box = Part.makeBox(w, d, h, origin)
    return shape.cut(box)

def cut_cylinder(shape, diameter, length, origin, direction=FreeCAD.Vector(0, 0, 1)):
    cyl = Part.makeCylinder(diameter / 2.0, length, origin, direction)
    return shape.cut(cyl)

# ============================================================
# Geometry parameters (all from machine_datums HMI_* block)
# ============================================================
FRAME_W           = MD.HMI_FRAME_W
FRAME_H           = MD.HMI_FRAME_H
FRAME_T           = MD.HMI_FRAME_T
TAB_HEIGHT        = MD.HMI_FRAME_TAB_HEIGHT
BEAM_BOLT_Z_TOP   = MD.HMI_FRAME_BEAM_BOLT_Z

# Screen
TOUCH_W           = MD.HMI_TOUCH_W
TOUCH_H           = MD.HMI_TOUCH_H

# Beam mount: 4 of 6 FRONT-face inserts (skip middle pair)
FRONT_PITCH       = MD.HMI_FRONT_INSERT_PITCH                     # 22
BEAM_BOLT_XS      = (-1.5 * FRONT_PITCH, -2.5 * FRONT_PITCH,      # -33, -55
                     +1.5 * FRONT_PITCH, +2.5 * FRONT_PITCH)      # +33, +55
M5_BOLT_D         = MD.HMI_M5_THROUGH_D

# Screen mount: 4 corner WINDOWS (M2.5 + fender washer when needed).
# Frame nominal = ELECROW RC070S measured PCD 79.45 x 64.4 mm (from
# the manufacturer's drawing, rounded to 80 x 64 mm).  The window
# adjustment range also accommodates VESA-75 and most other 7" patterns.
SCREEN_PCD_X_NOM  = MD.HMI_TOUCH_PCD_X_NOMINAL                # 80 (ELECROW)
SCREEN_PCD_Y_NOM  = MD.HMI_TOUCH_PCD_Y_NOMINAL                # 64 (ELECROW)
WIN_W             = MD.HMI_TOUCH_WIN_W                        # 30 mm in X
WIN_H             = MD.HMI_TOUCH_WIN_H                        # 30 mm in Z
M2_5_CLEAR_D      = MD.HMI_M2_5_CLEAR_D

# Cable cutout (bottom edge)
CABLE_CUT_W       = MD.HMI_FRAME_CABLE_CUT_W
CABLE_CUT_H       = MD.HMI_FRAME_CABLE_CUT_H

# Boolean / overcut helpers
EPS_OVERCUT       = MD.HMI_BOOLEAN_OVERCUT
CUT_EXTRA         = MD.HMI_CUT_EXTRA

# Derived: screen vertical centerline (within frame Z)
# Tab band is the top 18 mm; screen seats below it with some breathing gap.
TAB_BAND_BOTTOM_Z = FRAME_H - TAB_HEIGHT                            # 112
SCREEN_TOP_GAP    = MD.HMI_TOUCH_TOP_MARGIN
SCREEN_TOP_Z      = TAB_BAND_BOTTOM_Z - SCREEN_TOP_GAP              # 111
SCREEN_CENTER_Z   = SCREEN_TOP_Z - TOUCH_H / 2.0                    # 61
WIN_TOP_Z         = SCREEN_CENTER_Z + SCREEN_PCD_Y_NOM / 2.0        # 85.5
WIN_BOT_Z         = SCREEN_CENTER_Z - SCREEN_PCD_Y_NOM / 2.0        # 36.5
BEAM_BOLT_Z       = FRAME_H - BEAM_BOLT_Z_TOP                       # 123

# PCD adjustment range (for documentation/banner)
PCD_X_MIN         = max(0.0, SCREEN_PCD_X_NOM - WIN_W)
PCD_X_MAX         = SCREEN_PCD_X_NOM + WIN_W
PCD_Y_MIN         = max(0.0, SCREEN_PCD_Y_NOM - WIN_H)
PCD_Y_MAX         = SCREEN_PCD_Y_NOM + WIN_H

# ============================================================
# Standard CSM V3 banner
# ============================================================
print("=" * 70)
print(f"CSM V3   Part {PART_NUMBER}   {PART_NAME}   {VERSION}   [{STATUS}]")
print("=" * 70)
print(f"  Material:   {PRINT_MATERIAL}")
print(f"  Print:      {PRINT_INFILL} infill, {PRINT_WALLS} walls, {PRINT_LAYER} layers")
print(f"  Quantity:   {PRINT_QTY}")
print()
print("WALL-THICKNESS CHECK:")
top_to_beam_bolt        = FRAME_H - BEAM_BOLT_Z - M5_BOLT_D / 2.0       # frame top to bolt edge
beam_bolt_to_tab_bottom = BEAM_BOLT_Z - M5_BOLT_D / 2.0 - TAB_BAND_BOTTOM_Z
side_to_outer_bolt      = FRAME_W / 2.0 - max(abs(x) for x in BEAM_BOLT_XS) - M5_BOLT_D / 2.0
bolt_spacing            = (sorted(BEAM_BOLT_XS)[1] - sorted(BEAM_BOLT_XS)[0]) - M5_BOLT_D
top_to_window_top       = FRAME_H - (WIN_TOP_Z + WIN_H / 2.0)
window_bot_to_cable_top = (WIN_BOT_Z - WIN_H / 2.0) - CABLE_CUT_H
side_to_window_outer    = FRAME_W / 2.0 - (SCREEN_PCD_X_NOM / 2.0 + WIN_W / 2.0)
inner_window_gap        = SCREEN_PCD_X_NOM - WIN_W                              # X gap between L/R windows
inner_window_gap_z      = SCREEN_PCD_Y_NOM - WIN_H                              # Z gap between top/bot windows
tab_band_to_window_top  = TAB_BAND_BOTTOM_Z - (WIN_TOP_Z + WIN_H / 2.0)
checks = [
    ("Top edge to beam bolt (Z)",          top_to_beam_bolt,        3.0),
    ("Beam bolt to tab-band bottom (Z)",   beam_bolt_to_tab_bottom, 3.0),
    ("Side edge to outer beam bolt (X)",   side_to_outer_bolt,      3.0),
    ("Adjacent beam bolt spacing (X)",     bolt_spacing,            5.0),
    ("Top edge to window top (Z)",         top_to_window_top,       3.0),
    ("Window bottom to cable cutout (Z)",  window_bot_to_cable_top, 3.0),
    ("Side edge to window outer (X)",      side_to_window_outer,    5.0),
    ("Tab-band bottom to window top (Z)",  tab_band_to_window_top,  2.0),
    ("Inner spine between L/R windows (X)",inner_window_gap,        5.0),
    ("Inner spine between T/B windows (Z)",inner_window_gap_z,      5.0),
]
for label, val, min_ok in checks:
    flag = "OK " if val >= min_ok else "!! "
    print(f"  {flag}{label:42s} {val:6.2f} mm  (min {min_ok})")
print()
print("GEOMETRY:")
print(f"  plate:           {FRAME_W} x {FRAME_T} x {FRAME_H} mm")
print(f"  tab band:        top {TAB_HEIGHT} mm")
print(f"  beam mount:      4x M5 at X={BEAM_BOLT_XS}, Z={BEAM_BOLT_Z}")
print(f"  screen windows:  4x {WIN_W} x {WIN_H} mm at corners of nominal")
print(f"                   PCD {SCREEN_PCD_X_NOM} x {SCREEN_PCD_Y_NOM} (ELECROW RC070S nominal)")
print(f"  PCD coverage:")
print(f"    nominal:       {SCREEN_PCD_X_NOM} x {SCREEN_PCD_Y_NOM} mm (ELECROW RC070S, drawing 79.45 x 64.4)")
print(f"    adjustable:    X {PCD_X_MIN:.0f}-{PCD_X_MAX:.0f} mm, Y {PCD_Y_MIN:.0f}-{PCD_Y_MAX:.0f} mm")
print(f"    also fits:     - VESA-75 (75 x 75)")
print(f"                   - Raspberry Pi display patterns (58 x 49)")
print(f"                   - generic 7\" HDMI LCDs within range")
print(f"  cable cutout:    bottom edge, {CABLE_CUT_W} x {CABLE_CUT_H} mm")
print(f"  screen target:   {TOUCH_W} x {TOUCH_H} (ELECROW RC070S, B08FMNDDSL)")
print()

doc = FreeCAD.newDocument(PART_ID)

# ============================================================
# Build plate
# Origin at front-bottom-center: X = +/-FRAME_W/2, Y = 0 (back) to FRAME_T (front)
# but cleaner to put origin at plate center XZ on back face.
# Actually use: X = +/-FRAME_W/2, Y = -FRAME_T/2 to +FRAME_T/2, Z = 0 to FRAME_H
# Local convention: bottom of plate at Z=0, top at Z=FRAME_H, front at Y=-FRAME_T/2.
# ============================================================
plate = Part.makeBox(FRAME_W, FRAME_T, FRAME_H,
                     FreeCAD.Vector(-FRAME_W/2.0, -FRAME_T/2.0, 0))

# Beam mount through-holes (Y direction = full thickness)
for bx in BEAM_BOLT_XS:
    plate = cut_cylinder(plate, M5_BOLT_D, FRAME_T + 2 * CUT_EXTRA,
                          FreeCAD.Vector(bx, -FRAME_T/2.0 - CUT_EXTRA, BEAM_BOLT_Z),
                          FreeCAD.Vector(0, 1, 0))

# Screen mount: 4 corner WINDOWS (each WIN_W x WIN_H, cut full Y thickness)
# Use M2.5 screw + small fender washer (~10 mm OD) to clamp anywhere
# within the window.  Covers any PCD inside the adjustment range.
for sx in (-1, +1):
    for sz in (-1, +1):
        cx = sx * (SCREEN_PCD_X_NOM / 2.0)
        cz = SCREEN_CENTER_Z + sz * (SCREEN_PCD_Y_NOM / 2.0)
        plate = cut_box(plate, WIN_W, FRAME_T + 2 * EPS_OVERCUT, WIN_H,
                         FreeCAD.Vector(cx - WIN_W/2.0,
                                         -FRAME_T/2.0 - EPS_OVERCUT,
                                         cz - WIN_H/2.0))

# Cable cutout (bottom edge, full Y depth)
plate = cut_box(plate, CABLE_CUT_W, FRAME_T + 2 * EPS_OVERCUT, CABLE_CUT_H + EPS_OVERCUT,
                 FreeCAD.Vector(-CABLE_CUT_W/2.0,
                                 -FRAME_T/2.0 - EPS_OVERCUT,
                                 -EPS_OVERCUT))

# Export
obj = doc.addObject("Part::Feature", PART_ID)
obj.Shape = plate
if FreeCAD.GuiUp and obj.ViewObject is not None:
    obj.ViewObject.ShapeColor = (0.45, 0.55, 0.80)
doc.recompute()

BASE = os.path.dirname(os.path.dirname(os.path.abspath(__file__)))
OUT_STL  = os.path.join(BASE, PART_ID + ".stl")
OUT_STEP = os.path.join(BASE, PART_ID + ".step")
Part.export([obj], OUT_STL)
Part.export([obj], OUT_STEP)

try:
    com = plate.CenterOfMass
except AttributeError:
    com = plate.Solids[0].CenterOfMass if plate.Solids else None
print(f"[OK] STL:  {OUT_STL}")
print(f"[OK] STEP: {OUT_STEP}")
print(f"     volume: {plate.Volume:.0f} mm^3  (~{plate.Volume*1.27/1000:.1f}g PETG)")
if com is not None:
    print(f"     center of mass (frame-local):  X={com.x:+.2f}  Y={com.y:+.2f}  Z={com.z:+.2f} mm")
print()
print("ASSEMBLY:")
print(" 1. Print PETG flat on bed, 100% infill, 4 walls, 0.2 mm layers")
print("    (BACK face up so the window edges print clean)")
print(" 2. ELECROW RC070S official drawing confirms back-panel PCD =")
print("    79.45 x 64.4 mm. This frame nominal is 80 x 64 (centered).")
print("    Window range also accommodates Pi 4 (58 x 49), VESA-75 (75 x 75),")
print("    and most 7\" panel layouts -- X 50-110 mm, Y 34-94 mm.")
print(" 3. Thread 4x brass pillars (ELECROW kit) INTO the screen back")
print(" 4. Hold the screen behind the frame.  For each of the 4 pillars:")
print("    - Pass an M2.5 screw + small fender washer (~10 mm OD) through")
print("      the corner window from the FRONT face")
print("    - Thread into the pillar; snug -- the washer bridges the window")
print("      edges and clamps the position")
print(" 5. Connect HDMI + USB-C (power) -- cables hide in pillar gap")
print(" 6. Route cables DOWN through the bottom-edge cutout")
print(" 7. Bolt 4x M5 x 12 mm socket-head into beam FRONT face inserts")
print("    (at X = +/-33 and +/-55; skip the middle pair)")
print(" 8. Route HDMI and USB-C cables up the rear mast face, through the")
print("    Cross Beam cable channel, then forward to the Raspberry Pi Carrier")
print("    beneath the beam (cables enter Pi via the service opening on top)")
print("=" * 70)
