# -*- coding: utf-8 -*-
# =============================================================================
# CSM V3 -- 2020 ALUMINUM UPRIGHT V1.1  (precision frame, 1 of 4)
# =============================================================================
# One vertical 2020 aluminum extrusion. Four are used for the precision
# frame at corners of the wood upper deck. Placement (per macro instance,
# in assembly script): (±150, ±120, world Z = 18..206).
#
# CHANGES FROM V1.0
# -----------------
# - Length reduced 267 -> 188 mm (= MD.UPRIGHT_LEN per MACHINE_DATUMS R2).
# - World Z range now 18..206 (was -300..31).
# - Imports machine_datums.py (no hardcoded coordinates).
# - 4 corner-edge chamfers + 4 face T-slots retained from V1.0.
#
# Note: This macro outputs ONE upright. The Blender assembly script
# instantiates four copies at the four corner positions of the wood
# upper deck. Position constants live in MD.UPRIGHT_X_POSITIONS and
# MD.UPRIGHT_Y_POSITIONS.
#
# Reference: ICD R3 Interface 6 (frame architecture, precision uprights).
# =============================================================================

import FreeCAD, Part, os, sys

sys.path.insert(0, r"C:\3D-Project\00_PROJECT_OVERVIEW")
import machine_datums as MD

EXT_W       = MD.UPRIGHT_W           # 20.0
EXT_LEN     = MD.UPRIGHT_LEN         # 188.0
BOT_Z       = MD.UPRIGHT_BOT_Z       #  18.0 (= wood base top)
TOP_Z       = MD.UPRIGHT_TOP_Z       # 206.0
SLOT_OPEN   =  6.0                    # T-slot opening (visual)
SLOT_DEPTH  =  5.5                    # T-slot depth (visual)
CTR_BORE_D  =  4.2                    # center bore (cosmetic)
EDGE_CHAM   =  0.8                    # corner chamfer (cosmetic)
MATERIAL    = "Aluminum extrusion 6063-T5, anodized black"

print(f"[Upright_2020 V1.1]  {EXT_W} x {EXT_W} x {EXT_LEN} mm  ({MATERIAL})")
print(f"  world Z: bottom={BOT_Z}, top={TOP_Z}  (= MD.UPRIGHT_*_Z)")

doc = FreeCAD.newDocument("Upright2020_V1_1")

bar = Part.makeBox(EXT_W, EXT_W, EXT_LEN,
                   FreeCAD.Vector(-EXT_W/2, -EXT_W/2, BOT_Z))

# Center bore (cosmetic)
bore = Part.makeCylinder(CTR_BORE_D/2.0, EXT_LEN + 2.0,
                         FreeCAD.Vector(0, 0, BOT_Z - 1.0))
bar = bar.cut(bore)

# Four T-slot openings (one per face)
def slot_cut(face_axis, sign):
    if face_axis == 'x':
        sx = SLOT_DEPTH + 0.1
        sy = SLOT_OPEN
        cx = sign * (EXT_W/2 - SLOT_DEPTH/2.0) - (sign * 0.05)
        cy = 0.0
    else:
        sx = SLOT_OPEN
        sy = SLOT_DEPTH + 0.1
        cx = 0.0
        cy = sign * (EXT_W/2 - SLOT_DEPTH/2.0) - (sign * 0.05)
    return Part.makeBox(sx, sy, EXT_LEN + 2.0,
                        FreeCAD.Vector(cx - sx/2, cy - sy/2, BOT_Z - 1.0))

for ax, sgn in [('x', +1), ('x', -1), ('y', +1), ('y', -1)]:
    bar = bar.cut(slot_cut(ax, sgn))

# Optional edge chamfer at 4 vertical corners
try:
    edges = []
    for e in bar.Edges:
        v1, v2 = e.Vertexes[0].Point, e.Vertexes[1].Point
        if abs(v1.x - v2.x) < 0.01 and abs(v1.y - v2.y) < 0.01 and abs(v1.z - v2.z) > 100:
            if abs(abs(v1.x) - EXT_W/2) < 0.05 and abs(abs(v1.y) - EXT_W/2) < 0.05:
                edges.append(e)
    if edges:
        bar = bar.makeChamfer(EDGE_CHAM, edges)
        print(f"  chamfered {len(edges)} corner edges @ {EDGE_CHAM} mm")
except Exception as ex:
    print(f"  chamfer skipped: {ex}")

obj = doc.addObject("Part::Feature", "Upright_2020_V1_1")
obj.Shape = bar
doc.recompute()

BASE = os.path.dirname(os.path.dirname(os.path.abspath(__file__)))
OUT  = os.path.join(BASE, "CSM_V3_Upright2020_V1_1.stl")
Part.export([obj], OUT)
sz = os.path.getsize(OUT)
print(f"[OK] STL: {OUT}  ({sz} bytes, {sz/1024:.1f} KB)")
print(f"     volume: {bar.Volume:.0f} mm^3")
