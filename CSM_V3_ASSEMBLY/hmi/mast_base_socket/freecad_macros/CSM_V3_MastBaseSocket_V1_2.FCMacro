# -*- coding: utf-8 -*-
# =============================================================================
# CSM V3 -- MODULE 10 HMI -- MAST BASE SOCKET V1.2
# =============================================================================
# Full U-socket capturing one 2020 V-slot extrusion on all 4 sides.
# Two needed (left + right) at (X = +/-75, Y = -210) on wood base top.
#
# V1.2 CHANGES (engineering review of V1.1):
# -------------------------------------------------------
# 1. Pocket internal corner FILLETS (R1.5).  Better printability,
#    easier 2020 insertion, lower stress at four pocket corners.
# 2. Gussets enlarged 18 x 22 -> 25 x 30.  Stiffness up substantially,
#    material cost negligible.
# 3. Foot thickness 8 -> 10 mm.  More countersink margin, less flex
#    under repeated tightening of the four through-bolts.
# 4. Two ANTI-CREEP RIBS, 3 mm thick x 6 mm tall, running on foot top
#    from each socket Y-side to the outer pair of foot bolts.
#    Major bending-stiffness increase (the moment arm from mast top
#    is large; ribs prevent foot from levering off the wood).
# 5. Foot bolt RECESS: conical countersink -> straight COUNTERBORE
#    Ø9.5 x 5.5 deep for M5 socket-head cap screws.  Geometry now
#    matches the chosen fastener type.
# 6. Heat-set insert vertical pitch 10 -> 20 mm.  More room between
#    accessories, more flexibility for standard mounting patterns.
# 7. Helper cut_cylinder() introduced; bolt-hole loops simplified.
# 8. Spec banner & assembly notes refreshed for V1.2.
#
# Locked architecture (from V1.0/V1.1):
#   - U-pocket, 4 walls + closed bottom, open top
#   - Foot flange beneath, 4 M5 through-bolts into wood + nyloc below
#   - Triangular gussets both X sides
#   - Cable channel on REAR (+Y / cassette-facing) face
#   - 4 M5 heat-set INSERT pockets on FRONT (-Y / operator) face
#   - 2 M5 lateral bolts through FRONT wall into 2020 T-nuts
#   - Mast engagement 50 mm (kept from V1.1)
#
# Reference: ICD R7 Module 10 (HMI), dual 2020 mast at (X = +/-75, Y = -210)
# =============================================================================

import FreeCAD, Part, math, os, sys
sys.path.insert(0, r"C:\3D-Project\00_PROJECT_OVERVIEW")
import machine_datums as MD

# ============================================================
# Helpers
# ============================================================
def cut_cylinder(shape, diameter, length, origin, direction=FreeCAD.Vector(0, 0, 1)):
    """Cut a cylinder from `shape`.  Direction default +Z."""
    cyl = Part.makeCylinder(diameter / 2.0, length, origin, direction)
    return shape.cut(cyl)

# ============================================================
# HMI Module 10 -- locked geometry
# ============================================================
MAST_X_POS     = (+75.0, -75.0)
MAST_Y_POS     = -210.0
MAST_SPACING_X = 150.0
MAST_H         = 400.0

EXT_W          = 20.0
EXT_T          = 20.0
EXT_CLEAR      =  0.4

# ============================================================
# Socket (U-pocket)
# ============================================================
SOCKET_OUTER_W = 34.0
SOCKET_OUTER_T = 34.0
SOCKET_H       = 50.0
SOCKET_BOT_T   =  5.0
POCKET_W       = EXT_W + 2 * EXT_CLEAR
POCKET_T       = EXT_T + 2 * EXT_CLEAR
WALL_T         = (SOCKET_OUTER_W - POCKET_W) / 2.0
POCKET_FILLET_R = 1.5                     # V1.2 -- new

# ============================================================
# Foot flange  (V1.2: 8 -> 10 mm thick)
# ============================================================
FOOT_LEN       = 70.0
FOOT_W         = 50.0
FOOT_T         = 10.0                     # V1.2

# ============================================================
# Foot bolt holes  (V1.2: counterbore not CSK)
# ============================================================
M5_THROUGH_D   = 5.5
BOLT_CB_D      = 9.5                      # V1.2: counterbore Ø
BOLT_CB_H      = 5.5                      # V1.2: counterbore depth
FOOT_BOLT_DX   = 25.0
FOOT_BOLT_DY   = 17.0

# ============================================================
# Lateral 2020 bolt holes (unchanged)
# ============================================================
M5_T_BOLT_D    = 5.5
T_BOLT_Z1      = 12.0
T_BOLT_Z2      = 38.0

# ============================================================
# Gussets  (V1.2: enlarged 18 x 22 -> 25 x 30)
# ============================================================
GUSSET_BASE    = 25.0
GUSSET_RISE    = 30.0
GUSSET_T       =  6.0

# ============================================================
# Anti-creep ribs  (V1.2 -- new)
# Run on foot TOP from each socket Y-side wall to the outer bolts.
# Cross section 3 mm wide x 6 mm tall, length spans socket wall to
# beyond outer foot bolts (so they tie the bolt heads into the socket).
# ============================================================
RIB_T          =  3.0                     # rib thickness in Y
RIB_H          =  6.0                     # rib height above foot top
RIB_LEN        = FOOT_BOLT_DX + 10.0      # length in X, from socket center out
RIB_Y_OFFSET   = (SOCKET_OUTER_T / 2.0) - 1.0   # just inside socket Y wall

# ============================================================
# Cable channel on REAR (+Y) face
# ============================================================
CABLE_CH_W     =  8.0
CABLE_CH_D     =  4.0
CABLE_CH_H     = SOCKET_H + FOOT_T - 4.0

# ============================================================
# Expansion: M5 heat-set insert pockets on FRONT face
# V1.2: pitch 10 -> 20 mm (more room for standard accessories)
# ============================================================
INSERT_POCKET_D     =  6.2
INSERT_POCKET_H     =  8.5
EXP_INSERT_COUNT    =  4
EXP_INSERT_PITCH    = 20.0                # V1.2
EXP_INSERT_Z0_REL   =  6.0

MATERIAL = "PETG, 100% infill, 4 walls, 0.2 mm layers (Phase 1)"

# ============================================================
# Banner
# ============================================================
print("=" * 70)
print("CSM V3 -- HMI MODULE 10 -- Mast Base Socket V1.2")
print("=" * 70)
print(f"  material:         {MATERIAL}")
print(f"  socket outer:     {SOCKET_OUTER_W} x {SOCKET_OUTER_T} x {SOCKET_H} mm")
print(f"  pocket:           {POCKET_W:.1f} x {POCKET_T:.1f}, R{POCKET_FILLET_R} inner fillets")
print(f"  wall thickness:   {WALL_T:.1f} mm")
print(f"  foot:             {FOOT_LEN} x {FOOT_W} x {FOOT_T} mm  (V1.2: +2)")
print(f"  foot bolts:       4x M5, counterbore {BOLT_CB_D} x {BOLT_CB_H}")
print(f"  lateral bolts:    2x M5 through FRONT wall into 2020 T-nuts")
print(f"  gussets:          {GUSSET_BASE} x {GUSSET_RISE} x {GUSSET_T}  (V1.2: larger)")
print(f"  anti-creep ribs:  2x  {RIB_T} x {RIB_H} x {RIB_LEN*2:.0f}  (V1.2: new)")
print(f"  cable channel:    {CABLE_CH_W} x {CABLE_CH_D} on REAR face")
print(f"  expansion:        {EXP_INSERT_COUNT}x M5 inserts @ {EXP_INSERT_PITCH} pitch")
print(f"  install:          X = +/-75, Y = -210")
print(f"  quantity needed:  2 (left + right; same design)")

doc = FreeCAD.newDocument("MastBaseSocket_V1_2")

# ============================================================
# Build bracket
# Local frame: origin at center of socket footprint, on wood-base top.
#   X = tangential, Y = radial (+Y toward cassette), Z = vertical
# ============================================================

# --- FOOT FLANGE ---
foot = Part.makeBox(FOOT_LEN, FOOT_W, FOOT_T,
                    FreeCAD.Vector(-FOOT_LEN/2.0, -FOOT_W/2.0, 0))

# --- SOCKET BODY ---
socket_z = FOOT_T
socket = Part.makeBox(SOCKET_OUTER_W, SOCKET_OUTER_T, SOCKET_H,
                       FreeCAD.Vector(-SOCKET_OUTER_W/2.0,
                                       -SOCKET_OUTER_T/2.0, socket_z))

# --- POCKET CUT with rounded INNER corners (V1.2) ---
# Build rounded-corner rectangle profile and extrude downward into the
# socket.  4 vertical inner edges become R = POCKET_FILLET_R.
def rounded_rect_face(w, t, r):
    """Filleted-corner rectangle face in the XY plane, centered on origin."""
    hw = w / 2.0
    ht = t / 2.0
    # Straight segments + arc corners (Wire)
    p1 = FreeCAD.Vector(-hw + r, -ht, 0)
    p2 = FreeCAD.Vector( hw - r, -ht, 0)
    p3 = FreeCAD.Vector( hw,     -ht + r, 0)
    p4 = FreeCAD.Vector( hw,      ht - r, 0)
    p5 = FreeCAD.Vector( hw - r,  ht, 0)
    p6 = FreeCAD.Vector(-hw + r,  ht, 0)
    p7 = FreeCAD.Vector(-hw,      ht - r, 0)
    p8 = FreeCAD.Vector(-hw,     -ht + r, 0)
    # Arc midpoints (45 deg between adjacent corners)
    c_BR = FreeCAD.Vector( hw - r, -ht + r, 0)
    c_TR = FreeCAD.Vector( hw - r,  ht - r, 0)
    c_TL = FreeCAD.Vector(-hw + r,  ht - r, 0)
    c_BL = FreeCAD.Vector(-hw + r, -ht + r, 0)
    m_BR = c_BR + FreeCAD.Vector(r * math.cos(-math.pi/4), r * math.sin(-math.pi/4), 0)
    m_TR = c_TR + FreeCAD.Vector(r * math.cos( math.pi/4), r * math.sin( math.pi/4), 0)
    m_TL = c_TL + FreeCAD.Vector(r * math.cos( 3*math.pi/4), r * math.sin( 3*math.pi/4), 0)
    m_BL = c_BL + FreeCAD.Vector(r * math.cos(-3*math.pi/4), r * math.sin(-3*math.pi/4), 0)
    edges = [
        Part.LineSegment(p1, p2).toShape(),
        Part.Arc(p2, m_BR, p3).toShape(),
        Part.LineSegment(p3, p4).toShape(),
        Part.Arc(p4, m_TR, p5).toShape(),
        Part.LineSegment(p5, p6).toShape(),
        Part.Arc(p6, m_TL, p7).toShape(),
        Part.LineSegment(p7, p8).toShape(),
        Part.Arc(p8, m_BL, p1).toShape(),
    ]
    wire = Part.Wire(edges)
    return Part.Face(wire)

pocket_face = rounded_rect_face(POCKET_W, POCKET_T, POCKET_FILLET_R)
pocket_face.translate(FreeCAD.Vector(0, 0, socket_z + SOCKET_BOT_T))
pocket = pocket_face.extrude(FreeCAD.Vector(0, 0, SOCKET_H - SOCKET_BOT_T + 2))
socket = socket.cut(pocket)

bracket = foot.fuse(socket)

# --- TRIANGULAR GUSSETS on +X and -X faces  (V1.2: enlarged) ---
def make_gusset(sx):
    x_wall = sx * (SOCKET_OUTER_W / 2.0)
    p1 = FreeCAD.Vector(x_wall, 0, FOOT_T)
    p2 = FreeCAD.Vector(x_wall, 0, FOOT_T + GUSSET_RISE)
    p3 = FreeCAD.Vector(x_wall + sx * GUSSET_BASE, 0, FOOT_T)
    wire = Part.makePolygon([p1, p2, p3, p1])
    face = Part.Face(wire)
    gusset = face.extrude(FreeCAD.Vector(0, GUSSET_T, 0))
    gusset.translate(FreeCAD.Vector(0, -GUSSET_T / 2.0, 0))
    return gusset

for sx in (-1, +1):
    bracket = bracket.fuse(make_gusset(sx))

# --- ANTI-CREEP RIBS on foot top (V1.2 -- new) ---
# Two ribs, one at +Y inside edge of socket Y wall, one at -Y.
# Each rib spans from -RIB_LEN to +RIB_LEN in X, ties bolts to socket.
for sy in (-1, +1):
    rib = Part.makeBox(2 * RIB_LEN, RIB_T, RIB_H,
                        FreeCAD.Vector(-RIB_LEN,
                                        sy * RIB_Y_OFFSET - RIB_T/2.0,
                                        FOOT_T))
    bracket = bracket.fuse(rib)

# --- FOOT BOLT HOLES (M5 through + counterbore on top) ---
for sxf in (-1, +1):
    for syf in (-1, +1):
        hx = sxf * FOOT_BOLT_DX
        hy = syf * FOOT_BOLT_DY
        bracket = cut_cylinder(bracket, M5_THROUGH_D, FOOT_T + 4.0,
                                FreeCAD.Vector(hx, hy, -2.0))
        bracket = cut_cylinder(bracket, BOLT_CB_D, BOLT_CB_H + 0.1,
                                FreeCAD.Vector(hx, hy, FOOT_T - BOLT_CB_H))

# --- LATERAL 2020 BOLT HOLES (through FRONT wall, +Y into T-nut) ---
front_y = -SOCKET_OUTER_T / 2.0
for tz in (T_BOLT_Z1, T_BOLT_Z2):
    z_center = socket_z + SOCKET_BOT_T + tz
    bracket = cut_cylinder(bracket, M5_T_BOLT_D,
                            WALL_T + POCKET_T + WALL_T + 4.0,
                            FreeCAD.Vector(0, front_y - 2.0, z_center),
                            FreeCAD.Vector(0, 1, 0))

# --- CABLE CHANNEL on REAR (+Y) face ---
rear_y = SOCKET_OUTER_T / 2.0
ch = Part.makeBox(CABLE_CH_W, CABLE_CH_D + 0.1, CABLE_CH_H,
                   FreeCAD.Vector(-CABLE_CH_W / 2.0,
                                   rear_y - CABLE_CH_D,
                                   2.0))
bracket = bracket.cut(ch)

# --- HEAT-SET INSERT POCKETS on FRONT (-Y) face ---
for i in range(EXP_INSERT_COUNT):
    z = FOOT_T + EXP_INSERT_Z0_REL + i * EXP_INSERT_PITCH
    if z > FOOT_T + SOCKET_H - 5:
        continue
    bracket = cut_cylinder(bracket, INSERT_POCKET_D, INSERT_POCKET_H,
                            FreeCAD.Vector(0, front_y - 0.1, z),
                            FreeCAD.Vector(0, 1, 0))

# ============================================================
# V1.2 FILLETS -- foot/socket transition
# Same defensive approach as V1.1 (post-boolean fillet on selected edges).
# ============================================================
FILLET_R = 3.0

def _try_fillet(shape, radius, edge_filter, label):
    try:
        target = [e for e in shape.Edges if edge_filter(e)]
        if not target:
            print(f"  fillet[{label}]: no edges matched (skipped)")
            return shape
        filleted = shape.makeFillet(radius, target)
        print(f"  fillet[{label}] R{radius}: {len(target)} edges OK")
        return filleted
    except Exception as ex:
        print(f"  fillet[{label}] failed ({ex.__class__.__name__}): skipped")
        return shape

def _at_socket_root(edge):
    v1, v2 = edge.Vertexes[0].Point, edge.Vertexes[1].Point
    if abs(v1.z - FOOT_T) > 0.1 or abs(v2.z - FOOT_T) > 0.1:
        return False
    if edge.Length < 5.0 or edge.Length > FOOT_LEN + 5:
        return False
    return True

bracket = _try_fillet(bracket, FILLET_R, _at_socket_root, "socket-root")

# ============================================================
# Export STL + STEP
# ============================================================
obj = doc.addObject("Part::Feature", "MastBaseSocket_V1_2")
obj.Shape = bracket
if FreeCAD.GuiUp and obj.ViewObject is not None:
    obj.ViewObject.ShapeColor = (0.35, 0.50, 0.85)
doc.recompute()

BASE = os.path.dirname(os.path.dirname(os.path.abspath(__file__)))
OUT_STL  = os.path.join(BASE, "CSM_V3_MastBaseSocket_V1_2.stl")
OUT_STEP = os.path.join(BASE, "CSM_V3_MastBaseSocket_V1_2.step")
Part.export([obj], OUT_STL)
Part.export([obj], OUT_STEP)
sz_stl  = os.path.getsize(OUT_STL)
sz_step = os.path.getsize(OUT_STEP)
print(f"[OK] STL:  {OUT_STL}  ({sz_stl/1024:.1f} KB)")
print(f"[OK] STEP: {OUT_STEP} ({sz_step/1024:.1f} KB)")
print(f"     volume: {bracket.Volume:.0f} mm^3  (~{bracket.Volume*1.27/1000:.1f}g PETG)")
print()
print("ASSEMBLY (per bracket -- print 2):")
print(" 1. Print PETG 100% infill, 4 walls, 0.2 mm layers, foot DOWN")
print(" 2. Slide 2 M5 T-nuts into 2020 FRONT slot (-Y face)")
print(" 3. Stand 2020 upright; slide bracket pocket down over 2020 base")
print(" 4. 2 M5 x 12 mm socket-head bolts through bracket FRONT into T-nuts")
print(" 5. Place bracket at (X = +75 or -75, Y = -210) on wood base top")
print(" 6. Mark + drill 4 x Ø5.5 holes through wood under foot bolt grid")
print(" 7. 4 M5 x 30 mm socket-head bolts through foot counterbores")
print(" 8. Steel washer + M5 nyloc nut underneath wood base; tighten")
print(" 9. Verify 2020 stands square (vs wood base AND aluminum plate)")
print("10. Heat 4 M5 brass inserts (B0DPQJ4W3Z) into FRONT-face pockets")
print("    at ~220 C, ~30 s each")
print()
print("EXPANSION (4 M5 heat-set inserts on FRONT, 20 mm pitch):")
print("    - Camera mount, LED strip, status panel, sensors, etc.")
print("    - 20 mm pitch matches many standard accessory hole patterns")
print("=" * 70)
