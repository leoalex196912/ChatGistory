# -*- coding: utf-8 -*-
# =============================================================================
# CSM V3 -- SINKER RING V1.0
# =============================================================================
# File:    CSM_V3_SinkerRing_V1_0.FCMacro
# Date:    May 2026
# Target:  C:\3D-Project\01_MECHANICAL\07_KNITTING\freecad_macros\
#
# DESIGN INTENT:
#   Stationary ring around rotating cylinder with 72 sinker projections.
#   Sinkers hold yarn loop while needle drops to form stitch.
#   6 feeder windows allow yarn entry without removing sinkers (tapered).
#
# CRITICAL DESIGN RULES:
#   - NEVER remove sinkers at feeder zones (only taper height)
#   - Sinkers offset by 2.5deg from needle slots (between needles)
#   - All 72 sinkers retain function
#   - Smoothstep tapers in feeder zones (no sharp transitions)
#
# DIMENSIONS (LOCKED):
#   Ring OD: 135mm
#   Ring ID: 114.8mm (0.5mm clearance over 114.3mm cylinder)
#   Height: 8mm
#   Sinker: 1.2mm wide x 3.0mm radial x 4mm tall (full)
#   Sinker height tapered to 2mm at feeder window centers
#   72 sinkers at 5deg pitch (360/72)
#   6 feeders at 60deg intervals (0, 60, 120, 180, 240, 300deg)
#   Window width: ~8mm circumferential at sinker tip radius
#
# MOUNTING:
#   3 dowel pins at PCD 125mm: 1 round + 2 slotted
#   Apply Loctite 603 for retention
# =============================================================================

import FreeCAD
import Part
import math
import os

# =============================================================================
# CONFIGURATION
# =============================================================================

# Output paths
BASE = r"C:\3D-Project\01_MECHANICAL\02_CASSETTE_HEAD\sinker_ring"
PATH_STL_FULL  = os.path.join(BASE, "CSM_V3_SinkerRing_V1_0_FULL.stl")
PATH_STL_SLICE = os.path.join(BASE, "CSM_V3_SinkerRing_V1_0_TESTSLICE.stl")

# Ensure output directory exists
try:
    os.makedirs(BASE, exist_ok=True)
except:
    pass

# =============================================================================
# DIMENSIONS (all in mm)
# =============================================================================

# Ring main body
RING_OD = 135.0
RING_ID = 114.8           # 0.5mm total clearance over 114.3mm cylinder
RING_HEIGHT = 8.0
RING_OUTER_R = RING_OD / 2  # 67.5mm
RING_INNER_R = RING_ID / 2  # 57.4mm

# Sinker dimensions and POSITIONING
# CRITICAL: Sinker projections must be ABOVE the cylinder body
# Cylinder body: Z=0 to Z=75mm
# Sinker ring: sits at Z=75 to Z=83mm (ABOVE cylinder)
# Sinker ring is NOT around the cylinder body - it's at the TOP
# Sinker projections extend INWARD over the open top of cylinder
# This is why they don't interfere with the rotating cylinder wall

NUM_SINKERS = 72
SINKER_PITCH_DEG = 360.0 / NUM_SINKERS  # 5.0deg
SINKER_PHASE_OFFSET_DEG = 2.5   # Offset from needle slot (between needles)

SINKER_WIDTH = 1.2        # mm circumferential thickness
SINKER_RADIAL_EXT = 3.0   # mm extension inward from RING_INNER_R
SINKER_HEIGHT_FULL = 4.0  # mm axial height (full sinkers)
SINKER_HEIGHT_MIN = 2.0   # mm axial height at feeder window center

# V1.0: Sinker projections at TOP of ring (above cylinder body)
# Ring is 8mm tall total
# Sinkers occupy upper 4mm: Z=4 to Z=8
# (When mounted, ring base is at cylinder top so sinkers are at Z=79-83)
SINKER_Z_BASE = 4.0       # Z position where sinker projections start (upper half of ring)
                          # NOTE: Sinkers project from the upper portion of the ring

# Sinker tip radius (where the holding edge sits)
SINKER_TIP_R = RING_INNER_R - SINKER_RADIAL_EXT  # 54.4mm

# Feeder windows
NUM_FEEDERS = 6
FEEDER_ANGLES = [0, 60, 120, 180, 240, 300]   # 60deg intervals
FEEDER_WINDOW_ARC_MM = 8.0   # mm circumferential at sinker tip radius
FEEDER_TAPER_RANGE_DEG = 5.0  # taper extends +/- 5deg from feeder center

# Calculate angular width of feeder window
# arc_length = radius * angle_rad
FEEDER_WINDOW_ANGLE_DEG = math.degrees(FEEDER_WINDOW_ARC_MM / RING_INNER_R)
# About 8deg

# Mounting pins
PCD_PINS = 125.0           # Pitch circle diameter for dowel pins
PIN_RADIUS = PCD_PINS / 2  # 62.5mm
PIN_HOLE_DIA = 4.2         # Slightly larger than 4mm pin (4.0+0.2 clearance)
PIN_HOLE_R = PIN_HOLE_DIA / 2
PIN_HOLE_DEPTH = RING_HEIGHT  # Through hole

# Pin positions (3 pins, 1 round + 2 slotted)
# Place at 30deg, 150deg, 270deg (between feeders)
PIN_ANGLES = [30, 150, 270]
PIN_SLOT_LENGTH = 0.6   # mm - slot extends 0.3mm each side for thermal expansion

# Test slice angles
TEST_SLICE_START = -15.0  # deg (covers feeder at 0deg)
TEST_SLICE_END = 15.0

# Resolution
ANGULAR_SEGMENTS = 360  # 1deg segments for smooth ring

# =============================================================================
# UTILITY FUNCTIONS
# =============================================================================

def smoothstep(x):
    """Cubic smoothstep easing: f(x) = 3x^2 - 2x^3
    f(0)=0, f(1)=1, f'(0)=0, f'(1)=0
    Used for taper transitions to eliminate jerk."""
    if x <= 0:
        return 0.0
    if x >= 1:
        return 1.0
    return 3 * x * x - 2 * x * x * x


def get_sinker_height(theta_deg):
    """Returns sinker height at given angle.
    
    Outside feeder zones: SINKER_HEIGHT_FULL (4mm)
    At feeder centers: SINKER_HEIGHT_MIN (2mm)
    Smoothstep taper between.
    """
    # Find closest feeder angle
    min_dist = 360.0
    for fa in FEEDER_ANGLES:
        dist = abs(theta_deg - fa)
        # Handle wraparound (e.g., 358 is close to 0)
        if dist > 180:
            dist = 360 - dist
        if dist < min_dist:
            min_dist = dist
    
    # If outside taper range, full height
    if min_dist >= FEEDER_TAPER_RANGE_DEG:
        return SINKER_HEIGHT_FULL
    
    # Within taper range - smoothstep from MIN at 0deg to FULL at TAPER_RANGE
    progress = min_dist / FEEDER_TAPER_RANGE_DEG  # 0 at center, 1 at edge
    height_diff = SINKER_HEIGHT_FULL - SINKER_HEIGHT_MIN
    return SINKER_HEIGHT_MIN + height_diff * smoothstep(progress)


# =============================================================================
# BUILD SINKER RING
# =============================================================================

def build_sinker_ring(slice_only=False):
    """Build the sinker ring with all 72 sinker projections.
    
    Args:
        slice_only: if True, build only the test slice (30deg)
    
    Returns:
        FreeCAD Part shape
    """
    # 1. Create base ring (cylinder with hole)
    if slice_only:
        # For test slice, we need a sector
        slice_angle = TEST_SLICE_END - TEST_SLICE_START  # 30deg
        # Create sector by intersection
        full_outer = Part.makeCylinder(RING_OUTER_R, RING_HEIGHT)
        full_inner = Part.makeCylinder(RING_INNER_R, RING_HEIGHT + 0.1,
                                       FreeCAD.Vector(0, 0, -0.05))
        full_ring = full_outer.cut(full_inner)
        
        # Create sector cutter (large pie slice)
        sector = Part.makeCylinder(RING_OUTER_R + 10, RING_HEIGHT + 0.2,
                                   FreeCAD.Vector(0, 0, -0.1),
                                   FreeCAD.Vector(0, 0, 1),
                                   slice_angle)
        sector.rotate(FreeCAD.Vector(0, 0, 0),
                     FreeCAD.Vector(0, 0, 1),
                     TEST_SLICE_START)
        
        ring = full_ring.common(sector)
    else:
        # Full ring
        outer_cyl = Part.makeCylinder(RING_OUTER_R, RING_HEIGHT)
        inner_cyl = Part.makeCylinder(RING_INNER_R, RING_HEIGHT + 0.1,
                                      FreeCAD.Vector(0, 0, -0.05))
        ring = outer_cyl.cut(inner_cyl)
    
    # 2. Add 72 sinker projections
    sinkers_added = 0
    for i in range(NUM_SINKERS):
        # Sinker angular position (offset from needle slots)
        theta_deg = i * SINKER_PITCH_DEG + SINKER_PHASE_OFFSET_DEG
        # Normalize to 0-360
        theta_deg = theta_deg % 360
        
        # Skip if this sinker is outside test slice region
        if slice_only:
            if not (TEST_SLICE_START <= theta_deg <= TEST_SLICE_END):
                # Also check wraparound
                norm_theta = theta_deg if theta_deg <= 180 else theta_deg - 360
                if not (TEST_SLICE_START <= norm_theta <= TEST_SLICE_END):
                    continue
        
        # Get sinker height (tapered near feeders)
        height = get_sinker_height(theta_deg)
        
        # Build sinker projection
        # Sinker is a small box: width (circumferential) x extension (radial) x height (axial)
        # Position: tip at SINKER_TIP_R, base at RING_INNER_R
        
        theta_rad = math.radians(theta_deg)
        
        # Half-width angle for sinker (1.2mm wide at tip radius)
        half_width_angle = math.degrees((SINKER_WIDTH / 2) / SINKER_TIP_R)
        
        # Build sinker as a small wedge using two cylinders
        # Outer cylinder reaches to RING_INNER_R + small overlap
        # Inner cylinder reaches to SINKER_TIP_R
        # Wedge angle = 2 * half_width_angle
        
        wedge_angle = 2 * half_width_angle
        
        # Create wedge cylinder shape
        sinker_outer = Part.makeCylinder(
            RING_INNER_R + 0.1,  # slight overlap with ring
            height,
            FreeCAD.Vector(0, 0, SINKER_Z_BASE),
            FreeCAD.Vector(0, 0, 1),
            wedge_angle
        )
        sinker_outer.rotate(
            FreeCAD.Vector(0, 0, 0),
            FreeCAD.Vector(0, 0, 1),
            theta_deg - half_width_angle
        )
        
        # Subtract inner part (creates ring-segment shape)
        sinker_inner = Part.makeCylinder(
            SINKER_TIP_R,
            height + 0.2,
            FreeCAD.Vector(0, 0, SINKER_Z_BASE - 0.1),
            FreeCAD.Vector(0, 0, 1),
            wedge_angle + 0.1
        )
        sinker_inner.rotate(
            FreeCAD.Vector(0, 0, 0),
            FreeCAD.Vector(0, 0, 1),
            theta_deg - half_width_angle - 0.05
        )
        
        sinker = sinker_outer.cut(sinker_inner)
        ring = ring.fuse(sinker)
        sinkers_added += 1
    
    # 3. Add mounting pin holes (only for full ring)
    if not slice_only:
        for angle_deg in PIN_ANGLES:
            angle_rad = math.radians(angle_deg)
            pin_x = PIN_RADIUS * math.cos(angle_rad)
            pin_y = PIN_RADIUS * math.sin(angle_rad)
            
            # Round hole for first pin, slotted for others
            if angle_deg == PIN_ANGLES[0]:
                # Round hole
                pin_hole = Part.makeCylinder(
                    PIN_HOLE_R,
                    PIN_HOLE_DEPTH + 0.1,
                    FreeCAD.Vector(pin_x, pin_y, -0.05)
                )
            else:
                # Slotted hole - elongated tangentially for thermal expansion
                # Make a stadium shape (rectangle with rounded ends)
                # For simplicity, use 2 cylinders + a box
                tangent_angle_rad = angle_rad + math.pi/2
                offset_x = (PIN_SLOT_LENGTH/2) * math.cos(tangent_angle_rad)
                offset_y = (PIN_SLOT_LENGTH/2) * math.sin(tangent_angle_rad)
                
                # Two end cylinders
                hole1 = Part.makeCylinder(
                    PIN_HOLE_R,
                    PIN_HOLE_DEPTH + 0.1,
                    FreeCAD.Vector(pin_x + offset_x, pin_y + offset_y, -0.05)
                )
                hole2 = Part.makeCylinder(
                    PIN_HOLE_R,
                    PIN_HOLE_DEPTH + 0.1,
                    FreeCAD.Vector(pin_x - offset_x, pin_y - offset_y, -0.05)
                )
                pin_hole = hole1.fuse(hole2)
            
            ring = ring.cut(pin_hole)
    
    return ring, sinkers_added


# =============================================================================
# PRINT SUMMARY
# =============================================================================

print("=" * 70)
print("CSM V3 - SINKER RING V1.0")
print("=" * 70)
print(f"  Ring OD:                {RING_OD}mm")
print(f"  Ring ID:                {RING_ID}mm (0.5mm over cylinder)")
print(f"  Ring height:            {RING_HEIGHT}mm")
print(f"  Wall thickness:         {RING_OUTER_R - RING_INNER_R:.1f}mm")
print()
print(f"  Sinkers:                {NUM_SINKERS} at {SINKER_PITCH_DEG}deg pitch")
print(f"  Sinker offset:          {SINKER_PHASE_OFFSET_DEG}deg from needle slots")
print(f"  Sinker dimensions:      {SINKER_WIDTH}mm wide x {SINKER_RADIAL_EXT}mm long")
print(f"  Sinker tip radius:      {SINKER_TIP_R}mm")
print(f"  Sinker height (full):   {SINKER_HEIGHT_FULL}mm")
print(f"  Sinker height (taper):  {SINKER_HEIGHT_MIN}mm at feeder centers")
print(f"  Taper range:            +/-{FEEDER_TAPER_RANGE_DEG}deg from feeder")
print(f"  Taper easing:           SMOOTHSTEP cubic (jerk-free)")
print()
print(f"  Feeders:                {NUM_FEEDERS} at 60deg intervals")
print(f"  Feeder angles:          {FEEDER_ANGLES}")
print(f"  Window arc width:       {FEEDER_WINDOW_ARC_MM}mm ({FEEDER_WINDOW_ANGLE_DEG:.2f}deg)")
print()
print(f"  Mounting pins:          3 at PCD {PCD_PINS}mm")
print(f"  Pin angles:             {PIN_ANGLES}")
print(f"  Pin pattern:            1 round + 2 slotted (thermal compensation)")
print()

# =============================================================================
# BUILD AND EXPORT
# =============================================================================

doc = FreeCAD.newDocument("CSM_SinkerRing_V1_0")

# Build full ring
print("Building full sinker ring...")
ring_full, count_full = build_sinker_ring(slice_only=False)
print(f"  Created {count_full} sinker projections")

obj_full = doc.addObject("Part::Feature", "SinkerRing_V1_0_FULL")
obj_full.Shape = ring_full
print(f"  Full ring volume: {ring_full.Volume:.0f} mm^3")

# Build test slice
print()
print("Building test slice (30deg sector)...")
ring_slice, count_slice = build_sinker_ring(slice_only=True)
print(f"  Created {count_slice} sinker projections in test slice")

obj_slice = doc.addObject("Part::Feature", "SinkerRing_V1_0_TESTSLICE")
obj_slice.Shape = ring_slice
# Move slice to side for visibility
obj_slice.Placement.Base = FreeCAD.Vector(150, 0, 0)
print(f"  Test slice volume: {ring_slice.Volume:.0f} mm^3")

doc.recompute()

# Export STL files
print()
print("Exporting STL files...")
try:
    import Mesh
    
    # Full ring
    mesh_full = doc.addObject("Mesh::Feature", "Mesh_Full")
    mesh_full.Mesh = Mesh.Mesh(ring_full.tessellate(0.05))
    Mesh.export([mesh_full], PATH_STL_FULL)
    print(f"  Exported: {PATH_STL_FULL}")
    
    # Test slice
    mesh_slice = doc.addObject("Mesh::Feature", "Mesh_Slice")
    mesh_slice.Mesh = Mesh.Mesh(ring_slice.tessellate(0.05))
    Mesh.export([mesh_slice], PATH_STL_SLICE)
    print(f"  Exported: {PATH_STL_SLICE}")
    
except Exception as e:
    print(f"  STL export skipped: {e}")
    print(f"  Manually export from FreeCAD: File -> Export -> STL")

# Set view
try:
    import FreeCADGui
    FreeCADGui.SendMsgToActiveView("ViewFit")
    FreeCADGui.activeDocument().activeView().viewIsometric()
except:
    pass

print()
print("=" * 70)
print("SINKER RING V1.0 COMPLETE")
print("=" * 70)
print()
print("FILES CREATED:")
print(f"  {PATH_STL_FULL}")
print(f"  {PATH_STL_SLICE}")
print()
print("PRINT INSTRUCTIONS:")
print("  Material:     PETG (DRY!)")
print("  Layer height: 0.16mm")
print("  Perimeters:   4")
print("  Top/bottom:   5 layers")
print("  Infill:       30-40% Gyroid")
print("  Orientation:  Lying flat (sinkers pointing up)")
print("  Supports:     NONE")
print("  Print speed:  Outer wall 25mm/s, others 50mm/s")
print()
print("PRINT FIRST: Test slice (30deg, ~45min, ~25g PETG)")
print("THEN:        Full ring (~3-4hrs, ~140g PETG)")
print()
print("FINISHING:")
print("  1. Light sand sinker tips (1000-grit)")
print("  2. Test fit over cylinder (should slide smoothly)")
print("  3. Apply PTFE lubricant to sinker contact surfaces")
