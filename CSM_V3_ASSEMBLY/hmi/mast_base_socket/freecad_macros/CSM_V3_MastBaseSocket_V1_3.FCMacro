# -*- coding: utf-8 -*-
# =============================================================================
# CSM V3 -- MODULE 10 HMI -- MAST BASE SOCKET V1.3  (FREEZE CANDIDATE)
# =============================================================================
# Final freeze revision over V1.2 per engineering review:
#
# V1.3 CHANGES:
#   1. 1 mm stepped lead-in CHAMFER at pocket entry (open top of socket).
#      Easier 2020 insertion, traps no elephant-foot at entry.
#   2. Ø3 DRAIN HOLE through closed pocket floor, exiting via foot bottom.
#      Lets support fragments / strings / moisture escape.
#   3. RIB-to-GUSSET BLEND: 2 straight foot-top ribs replaced with 4
#      DIAGONAL ribs running from each outer foot bolt to the gusset
#      foot-attach line on the same socket X-face.  Load now flows:
#         bolt -> rib -> gusset -> socket -> mast
#      with a smoother stress path.
#   4. WALL-THICKNESS verification block prints all critical ligaments.
#
# All V1.2 features retained: 50 mm engagement, 10 mm foot, 25x30 gussets,
# R1.5 pocket inner fillets, counterbore for socket-head, 20 mm insert pitch,
# cable channel, heat-set inserts.
# =============================================================================

import FreeCAD, Part, math, os, sys
sys.path.insert(0, r"C:\3D-Project\00_PROJECT_OVERVIEW")
import machine_datums as MD

# ============================================================
# PART METADATA (CSM V3 macro standard header)
# ============================================================
PART_NUMBER     = "M10-P01"
PART_NAME       = "Mast Base Socket"
VERSION         = "V1.3"
STATUS          = "FROZEN"
PART_ID         = "CSM_V3_MastBaseSocket_V1_3"   # filename root
PRINT_QTY       = 2
PRINT_MATERIAL  = "PETG (PA12 production)"
PRINT_INFILL    = "100%"
PRINT_LAYER     = "0.20 mm"
PRINT_WALLS     = 4

# ============================================================
# Helpers
# ============================================================
def cut_cylinder(shape, diameter, length, origin, direction=FreeCAD.Vector(0, 0, 1)):
    cyl = Part.makeCylinder(diameter / 2.0, length, origin, direction)
    return shape.cut(cyl)

def rounded_rect_face(w, t, r):
    hw, ht = w / 2.0, t / 2.0
    p1 = FreeCAD.Vector(-hw + r, -ht, 0)
    p2 = FreeCAD.Vector( hw - r, -ht, 0)
    p3 = FreeCAD.Vector( hw,     -ht + r, 0)
    p4 = FreeCAD.Vector( hw,      ht - r, 0)
    p5 = FreeCAD.Vector( hw - r,  ht, 0)
    p6 = FreeCAD.Vector(-hw + r,  ht, 0)
    p7 = FreeCAD.Vector(-hw,      ht - r, 0)
    p8 = FreeCAD.Vector(-hw,     -ht + r, 0)
    c_BR = FreeCAD.Vector( hw - r, -ht + r, 0)
    c_TR = FreeCAD.Vector( hw - r,  ht - r, 0)
    c_TL = FreeCAD.Vector(-hw + r,  ht - r, 0)
    c_BL = FreeCAD.Vector(-hw + r, -ht + r, 0)
    m_BR = c_BR + FreeCAD.Vector(r * math.cos(-math.pi/4), r * math.sin(-math.pi/4), 0)
    m_TR = c_TR + FreeCAD.Vector(r * math.cos( math.pi/4), r * math.sin( math.pi/4), 0)
    m_TL = c_TL + FreeCAD.Vector(r * math.cos( 3*math.pi/4), r * math.sin( 3*math.pi/4), 0)
    m_BL = c_BL + FreeCAD.Vector(r * math.cos(-3*math.pi/4), r * math.sin(-3*math.pi/4), 0)
    edges = [
        Part.LineSegment(p1, p2).toShape(),
        Part.Arc(p2, m_BR, p3).toShape(),
        Part.LineSegment(p3, p4).toShape(),
        Part.Arc(p4, m_TR, p5).toShape(),
        Part.LineSegment(p5, p6).toShape(),
        Part.Arc(p6, m_TL, p7).toShape(),
        Part.LineSegment(p7, p8).toShape(),
        Part.Arc(p8, m_BL, p1).toShape(),
    ]
    return Part.Face(Part.Wire(edges))

# ============================================================
# Geometry parameters -- all from machine_datums.py (HMI block)
# ============================================================
EXT_W           = MD.HMI_EXT_W
EXT_T           = MD.HMI_EXT_W
EXT_CLEAR       = MD.HMI_EXT_CLEAR
SOCKET_OUTER_W  = MD.HMI_SOCKET_OUTER_W
SOCKET_OUTER_T  = MD.HMI_SOCKET_OUTER_T
SOCKET_H        = MD.HMI_SOCKET_H
SOCKET_BOT_T    = MD.HMI_SOCKET_BOT_T
POCKET_W        = MD.HMI_POCKET_W
POCKET_T        = MD.HMI_POCKET_W
WALL_T          = (SOCKET_OUTER_W - POCKET_W) / 2.0
POCKET_FILLET_R = MD.HMI_SOCKET_POCKET_R
CHAMFER_SIZE    = MD.HMI_POCKET_CHAMFER

FOOT_LEN        = MD.HMI_FOOT_LEN
FOOT_W          = MD.HMI_FOOT_W
FOOT_T          = MD.HMI_FOOT_T
M5_THROUGH_D    = MD.HMI_M5_THROUGH_D
BOLT_CB_D       = MD.HMI_BOLT_CB_D
BOLT_CB_H       = MD.HMI_BOLT_CB_H
FOOT_BOLT_DX    = MD.HMI_FOOT_BOLT_DX
FOOT_BOLT_DY    = MD.HMI_FOOT_BOLT_DY

FRONT_BOSS_W         = MD.HMI_FRONT_BOSS_W
FRONT_BOSS_T         = MD.HMI_FRONT_BOSS_T
FRONT_BOSS_Z0_REL    = MD.HMI_FRONT_BOSS_Z0_REL
FRONT_BOSS_H_TOP_REL = MD.HMI_FRONT_BOSS_TOP_REL

M5_T_BOLT_D     = MD.HMI_M5_THROUGH_D
T_BOLT_Z1       = MD.HMI_T_BOLT_Z1
T_BOLT_Z2       = MD.HMI_T_BOLT_Z2

GUSSET_BASE     = MD.HMI_GUSSET_BASE
GUSSET_RISE     = MD.HMI_GUSSET_RISE
GUSSET_T        = MD.HMI_GUSSET_T

RIB_T                   = MD.HMI_RIB_T
RIB_H                   = MD.HMI_RIB_H
RIB_OVERLAP_INTO_GUSSET = MD.HMI_RIB_OVERLAP

CABLE_CH_W      = MD.HMI_CABLE_CH_W
CABLE_CH_D      = MD.HMI_CABLE_CH_D
CABLE_CH_H      = SOCKET_H + FOOT_T - 4.0       # derived (bracket-local)

INSERT_POCKET_D    = MD.HMI_INSERT_POCKET_D
INSERT_POCKET_H    = MD.HMI_INSERT_POCKET_H
EXP_INSERT_COUNT   = MD.HMI_EXP_INSERT_COUNT
EXP_INSERT_PITCH   = MD.HMI_EXP_INSERT_PITCH
EXP_INSERT_Z0_REL  = MD.HMI_EXP_INSERT_Z0_REL

DRAIN_D         = MD.HMI_DRAIN_D

# Boolean / overcut helpers (FDM print engineering)
EPS_OVERCUT     = MD.HMI_BOOLEAN_OVERCUT        # 0.1 mm past target face
CUT_EXTRA       = MD.HMI_CUT_EXTRA              # 2.0 mm through-cut margin
CUT_START_OFF   = MD.HMI_CUT_START_OFFSET       # 0.05 mm pre-face start

# ============================================================
# Standard CSM V3 banner
# ============================================================
print("=" * 70)
print(f"CSM V3   Part {PART_NUMBER}   {PART_NAME}   {VERSION}   [{STATUS}]")
print("=" * 70)
print(f"  Material:   {PRINT_MATERIAL}")
print(f"  Print:      {PRINT_INFILL} infill, {PRINT_WALLS} walls, {PRINT_LAYER} layers")
print(f"  Quantity:   {PRINT_QTY}")
print()
print("WALL-THICKNESS CHECK:")
wall_pocket_to_outer = WALL_T
foot_edge_to_bolt_x  = FOOT_LEN/2 - FOOT_BOLT_DX
foot_edge_to_bolt_y  = FOOT_W/2 - FOOT_BOLT_DY
bolt_wall_x          = foot_edge_to_bolt_x - BOLT_CB_D/2
bolt_wall_y          = foot_edge_to_bolt_y - BOLT_CB_D/2
socket_to_bolt_x     = FOOT_BOLT_DX - SOCKET_OUTER_W/2
socket_to_bolt_y     = FOOT_BOLT_DY - SOCKET_OUTER_T/2
front_wall_with_boss = WALL_T + FRONT_BOSS_T - INSERT_POCKET_H
checks = [
    ("Pocket wall (socket OD)",     wall_pocket_to_outer, 4.0),
    ("Foot edge to bolt CB (X)",    bolt_wall_x,          2.0),
    ("Foot edge to bolt CB (Y)",    bolt_wall_y,          2.0),
    ("Socket OD to bolt (X)",       socket_to_bolt_x,     2.0),
    ("Socket OD to bolt (Y)",       socket_to_bolt_y,     2.0),
    ("Front wall (with boss) behind insert",
                                    front_wall_with_boss, 1.0),
]
for label, val, min_ok in checks:
    flag = "OK " if val >= min_ok else "!! "
    print(f"  {flag}{label:42s} {val:6.2f} mm  (min {min_ok})")
print()
print("GEOMETRY:")
print(f"  socket outer:    {SOCKET_OUTER_W} sq x {SOCKET_H} mm")
print(f"  pocket:          {POCKET_W:.1f} sq, R{POCKET_FILLET_R} fillets, {CHAMFER_SIZE} mm lead-in")
print(f"  foot:            {FOOT_LEN} x {FOOT_W} x {FOOT_T}")
print(f"  gussets:         {GUSSET_BASE} x {GUSSET_RISE} x {GUSSET_T}")
print(f"  4x diagonal ribs:  {RIB_T} x {RIB_H} from outer bolts into gussets")
print(f"  drain hole:      D{DRAIN_D} through pocket floor")
print(f"  inserts:         {EXP_INSERT_COUNT}x M5 heat-set @ {EXP_INSERT_PITCH} mm pitch")
print()

doc = FreeCAD.newDocument(PART_ID)

# ============================================================
# Build bracket
# ============================================================
foot = Part.makeBox(FOOT_LEN, FOOT_W, FOOT_T,
                    FreeCAD.Vector(-FOOT_LEN/2.0, -FOOT_W/2.0, 0))

socket_z = FOOT_T
socket = Part.makeBox(SOCKET_OUTER_W, SOCKET_OUTER_T, SOCKET_H,
                       FreeCAD.Vector(-SOCKET_OUTER_W/2.0,
                                       -SOCKET_OUTER_T/2.0, socket_z))

# Pocket (main bore, top-open)
pocket_face = rounded_rect_face(POCKET_W, POCKET_T, POCKET_FILLET_R)
pocket_face.translate(FreeCAD.Vector(0, 0, socket_z + SOCKET_BOT_T))
pocket = pocket_face.extrude(FreeCAD.Vector(0, 0, SOCKET_H - SOCKET_BOT_T + CUT_EXTRA))
socket = socket.cut(pocket)

# V1.3: 1 mm stepped lead-in chamfer at pocket entry (top of socket)
chamfer_face = rounded_rect_face(POCKET_W + 2 * CHAMFER_SIZE,
                                   POCKET_T + 2 * CHAMFER_SIZE,
                                   POCKET_FILLET_R + CHAMFER_SIZE)
chamfer_top_z = socket_z + SOCKET_H - CHAMFER_SIZE
chamfer_face.translate(FreeCAD.Vector(0, 0, chamfer_top_z))
chamfer = chamfer_face.extrude(FreeCAD.Vector(0, 0, CHAMFER_SIZE + EPS_OVERCUT))
socket = socket.cut(chamfer)

bracket = foot.fuse(socket)

# Gussets (unchanged from V1.2)
def make_gusset(sx):
    x_wall = sx * (SOCKET_OUTER_W / 2.0)
    p1 = FreeCAD.Vector(x_wall, 0, FOOT_T)
    p2 = FreeCAD.Vector(x_wall, 0, FOOT_T + GUSSET_RISE)
    p3 = FreeCAD.Vector(x_wall + sx * GUSSET_BASE, 0, FOOT_T)
    wire = Part.makePolygon([p1, p2, p3, p1])
    face = Part.Face(wire)
    g = face.extrude(FreeCAD.Vector(0, GUSSET_T, 0))
    g.translate(FreeCAD.Vector(0, -GUSSET_T / 2.0, 0))
    return g

for sx in (-1, +1):
    bracket = bracket.fuse(make_gusset(sx))

# V1.3: FRONT FACE BOSS for heat-set inserts (local thickening)
boss_h = SOCKET_H - FRONT_BOSS_H_TOP_REL - FRONT_BOSS_Z0_REL
boss = Part.makeBox(FRONT_BOSS_W, FRONT_BOSS_T, boss_h,
                     FreeCAD.Vector(-FRONT_BOSS_W / 2.0,
                                     -SOCKET_OUTER_T / 2.0 - FRONT_BOSS_T,
                                     FOOT_T + FRONT_BOSS_Z0_REL))
bracket = bracket.fuse(boss)

# V1.3: 4 DIAGONAL RIBS  (corner bolts -> gusset attach on socket X face)
# Each rib is a thin slab on foot top, oriented along the line from
# (sxf * FOOT_BOLT_DX, syf * FOOT_BOLT_DY)  ->  (sxf * SOCKET_OUTER_W/2, 0)
# Slab thickness RIB_T perpendicular to that line, height RIB_H above foot.
def make_diagonal_rib(sxf, syf):
    start = FreeCAD.Vector(sxf * FOOT_BOLT_DX, syf * FOOT_BOLT_DY, FOOT_T)
    # End point reaches INSIDE the gusset by RIB_OVERLAP so rib feeds load
    # into gusset volume instead of butting against its edge.
    end   = FreeCAD.Vector(sxf * (SOCKET_OUTER_W / 2.0 - RIB_OVERLAP_INTO_GUSSET),
                            0, FOOT_T)
    dx, dy = end.x - start.x, end.y - start.y
    L = math.hypot(dx, dy)
    ux, uy = dx / L, dy / L
    px, py = -uy, ux                              # perpendicular in XY
    h = RIB_T / 2.0
    c1 = FreeCAD.Vector(start.x + px * h, start.y + py * h, FOOT_T)
    c2 = FreeCAD.Vector(end.x   + px * h, end.y   + py * h, FOOT_T)
    c3 = FreeCAD.Vector(end.x   - px * h, end.y   - py * h, FOOT_T)
    c4 = FreeCAD.Vector(start.x - px * h, start.y - py * h, FOOT_T)
    wire = Part.makePolygon([c1, c2, c3, c4, c1])
    face = Part.Face(wire)
    return face.extrude(FreeCAD.Vector(0, 0, RIB_H))

for sxf in (-1, +1):
    for syf in (-1, +1):
        bracket = bracket.fuse(make_diagonal_rib(sxf, syf))

# Foot bolt holes + counterbores (cut AFTER ribs so bolts pass through rib origin)
for sxf in (-1, +1):
    for syf in (-1, +1):
        hx = sxf * FOOT_BOLT_DX
        hy = syf * FOOT_BOLT_DY
        bracket = cut_cylinder(bracket, M5_THROUGH_D, FOOT_T + 2 * CUT_EXTRA,
                                FreeCAD.Vector(hx, hy, -CUT_EXTRA))
        bracket = cut_cylinder(bracket, BOLT_CB_D, BOLT_CB_H + EPS_OVERCUT,
                                FreeCAD.Vector(hx, hy, FOOT_T - BOLT_CB_H))

# Lateral 2020 bolts
front_y = -SOCKET_OUTER_T / 2.0
for tz in (T_BOLT_Z1, T_BOLT_Z2):
    z_center = socket_z + SOCKET_BOT_T + tz
    bracket = cut_cylinder(bracket, M5_T_BOLT_D,
                            FRONT_BOSS_T + WALL_T + POCKET_T + WALL_T + 2 * CUT_EXTRA,
                            FreeCAD.Vector(0, front_y - FRONT_BOSS_T - CUT_EXTRA, z_center),
                            FreeCAD.Vector(0, 1, 0))

# Cable channel (REAR)
rear_y = SOCKET_OUTER_T / 2.0
ch = Part.makeBox(CABLE_CH_W, CABLE_CH_D + EPS_OVERCUT, CABLE_CH_H,
                   FreeCAD.Vector(-CABLE_CH_W / 2.0,
                                   rear_y - CABLE_CH_D, CUT_EXTRA))
bracket = bracket.cut(ch)

# Heat-set insert pockets (FRONT)
for i in range(EXP_INSERT_COUNT):
    z = FOOT_T + EXP_INSERT_Z0_REL + i * EXP_INSERT_PITCH
    if z > FOOT_T + SOCKET_H - 5:
        continue
    bracket = cut_cylinder(bracket, INSERT_POCKET_D, INSERT_POCKET_H,
                            FreeCAD.Vector(0, front_y - FRONT_BOSS_T - EPS_OVERCUT, z),
                            FreeCAD.Vector(0, 1, 0))

# V1.3: Ø3 DRAIN HOLE through pocket floor (vertical, all the way through foot)
bracket = cut_cylinder(bracket, DRAIN_D, FOOT_T + SOCKET_BOT_T + CUT_EXTRA,
                        FreeCAD.Vector(0, 0, -CUT_EXTRA / 2.0))

# Defensive fillet at foot-socket transition (may skip on OCC error)
def _try_fillet(shape, radius, edge_filter, label):
    try:
        target = [e for e in shape.Edges if edge_filter(e)]
        if not target:
            print(f"  fillet[{label}]: no edges matched (skipped)")
            return shape
        filleted = shape.makeFillet(radius, target)
        print(f"  fillet[{label}] R{radius}: {len(target)} edges OK")
        return filleted
    except Exception as ex:
        print(f"  fillet[{label}] failed ({ex.__class__.__name__}): skipped")
        return shape

def _at_socket_root(edge):
    v1, v2 = edge.Vertexes[0].Point, edge.Vertexes[1].Point
    if abs(v1.z - FOOT_T) > 0.1 or abs(v2.z - FOOT_T) > 0.1:
        return False
    if edge.Length < 5.0 or edge.Length > FOOT_LEN + 5:
        return False
    return True

bracket = _try_fillet(bracket, 3.0, _at_socket_root, "socket-root")

# Export (filenames derived from PART_ID -- no drift on revision)
obj = doc.addObject("Part::Feature", PART_ID)
obj.Shape = bracket
if FreeCAD.GuiUp and obj.ViewObject is not None:
    obj.ViewObject.ShapeColor = (0.35, 0.50, 0.85)
doc.recompute()

BASE = os.path.dirname(os.path.dirname(os.path.abspath(__file__)))
OUT_STL  = os.path.join(BASE, PART_ID + ".stl")
OUT_STEP = os.path.join(BASE, PART_ID + ".step")
Part.export([obj], OUT_STL)
Part.export([obj], OUT_STEP)
try:
    com = bracket.CenterOfMass
except AttributeError:
    com = bracket.Solids[0].CenterOfMass if bracket.Solids else None
print(f"[OK] STL:  {OUT_STL}")
print(f"[OK] STEP: {OUT_STEP}")
print(f"     volume: {bracket.Volume:.0f} mm^3  (~{bracket.Volume*1.27/1000:.1f}g PETG)")
if com is not None:
    print(f"     center of mass (bracket-local):  X={com.x:+.2f}  Y={com.y:+.2f}  Z={com.z:+.2f} mm")
print("=" * 70)
