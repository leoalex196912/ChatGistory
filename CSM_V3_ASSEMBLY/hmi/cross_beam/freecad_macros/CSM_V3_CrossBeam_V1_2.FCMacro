# -*- coding: utf-8 -*-
# =============================================================================
# CSM V3 -- MODULE 10 HMI -- CROSS BEAM V1.2  (FREEZE CANDIDATE)
# =============================================================================
# Final freeze revision over V1.1 per engineering review:
#
# V1.2 CHANGES:
#   1. 1 mm stepped lead-in CHAMFER at mast pocket entry (bottom face).
#      Easier drop-over onto mast tops, anti elephant-foot at entry.
#   2. PI_PCD_Y corrected 49 -> 30 mm.  V1.1 spec'd 58 x 49 (real Pi 4
#      footprint) but inserts at +/-24.5 don't fit in a 40 mm-wide beam.
#      Beam now uses a 58 x 30 mount grid; Pi Carrier V1.0 (Module 10
#      Part 3) is the 58 x 30 (beam side) -> 58 x 49 (Pi 4 side) adapter.
#   3. WALL-THICKNESS verification block prints all critical ligaments.
#
# Otherwise identical to V1.1: 170 x 40 x 30 mm beam, deep mast pockets,
# closed ends, center service opening, counterbore for socket-head bolts,
# cable channel, 6x accessory inserts.
# =============================================================================

import FreeCAD, Part, math, os, sys
sys.path.insert(0, r"C:\3D-Project\00_PROJECT_OVERVIEW")
import machine_datums as MD

# ============================================================
# PART METADATA (CSM V3 macro standard header)
# ============================================================
PART_NUMBER     = "M10-P02"
PART_NAME       = "Cross Beam"
VERSION         = "V1.2"
STATUS          = "FROZEN"
PART_ID         = "CSM_V3_CrossBeam_V1_2"        # filename root
PRINT_QTY       = 1
PRINT_MATERIAL  = "PETG (PA12 production)"
PRINT_INFILL    = "100%"
PRINT_LAYER     = "0.20 mm"
PRINT_WALLS     = 4

def cut_cylinder(shape, diameter, length, origin, direction=FreeCAD.Vector(0, 0, 1)):
    cyl = Part.makeCylinder(diameter / 2.0, length, origin, direction)
    return shape.cut(cyl)

# ============================================================
# Geometry parameters -- all from machine_datums.py (HMI block)
# ============================================================
MAST_X_POS      = MD.HMI_MAST_X_POSITIONS
EXT_W           = MD.HMI_EXT_W
EXT_CLEAR       = MD.HMI_EXT_CLEAR

BEAM_LEN_X      = MD.HMI_BEAM_LEN_X
BEAM_W_Y        = MD.HMI_BEAM_W_Y
BEAM_H_Z        = MD.HMI_BEAM_H_Z

POCKET_W        = MD.HMI_POCKET_W
POCKET_T        = MD.HMI_POCKET_W
POCKET_DEPTH    = MD.HMI_BEAM_POCKET_DEPTH
CHAMFER_SIZE    = MD.HMI_POCKET_CHAMFER

MAST_BOLT_D     = MD.HMI_M5_THROUGH_D
BOLT_CB_D       = MD.HMI_BOLT_CB_D
BOLT_CB_H       = MD.HMI_BOLT_CB_H

INSERT_POCKET_D = MD.HMI_INSERT_POCKET_D
INSERT_POCKET_H = MD.HMI_INSERT_POCKET_H
PI_MOUNT_PCD_X  = MD.HMI_PI_MOUNT_PCD_X
PI_MOUNT_PCD_Y  = MD.HMI_PI_MOUNT_PCD_Y

CABLE_CH_W      = MD.HMI_CABLE_CH_W
CABLE_CH_D      = MD.HMI_CABLE_CH_D
END_MARGIN      = MD.HMI_BEAM_END_MARGIN
CABLE_CH_LEN_X  = BEAM_LEN_X - 2 * END_MARGIN

FRONT_INSERT_COUNT = MD.HMI_FRONT_INSERT_COUNT
FRONT_INSERT_PITCH = MD.HMI_FRONT_INSERT_PITCH
FRONT_INSERT_Z     = BEAM_H_Z / 2.0             # derived

SERVICE_OPEN_X  = MD.HMI_SERVICE_OPEN_X
SERVICE_OPEN_Y  = MD.HMI_SERVICE_OPEN_Y

# Boolean / overcut helpers (FDM print engineering)
EPS_OVERCUT     = MD.HMI_BOOLEAN_OVERCUT
CUT_EXTRA       = MD.HMI_CUT_EXTRA
CUT_START_OFF   = MD.HMI_CUT_START_OFFSET

# ============================================================
# Standard CSM V3 banner
# ============================================================
print("=" * 70)
print(f"CSM V3   Part {PART_NUMBER}   {PART_NAME}   {VERSION}   [{STATUS}]")
print("=" * 70)
print(f"  Material:   {PRINT_MATERIAL}")
print(f"  Print:      {PRINT_INFILL} infill, {PRINT_WALLS} walls, {PRINT_LAYER} layers")
print(f"  Quantity:   {PRINT_QTY}")
print()
print("WALL-THICKNESS CHECK:")
beam_y_wall = (BEAM_W_Y - POCKET_T) / 2.0
end_wall_x  = (BEAM_LEN_X - 2 * MAST_X_POS[0]) / 2.0 - POCKET_W / 2.0
pi_to_edge_y = BEAM_W_Y / 2.0 - PI_MOUNT_PCD_Y / 2.0 - INSERT_POCKET_D / 2.0
pi_to_svc_y  = PI_MOUNT_PCD_Y / 2.0 - SERVICE_OPEN_Y / 2.0 - INSERT_POCKET_D / 2.0
svc_to_pocket_x = MAST_X_POS[0] - POCKET_W / 2.0 - SERVICE_OPEN_X / 2.0
front_remaining = BEAM_W_Y / 2.0 + 0  # unused, kept for symmetry
material_above_pocket = BEAM_H_Z - POCKET_DEPTH
checks = [
    ("Beam Y wall around mast pocket",  beam_y_wall,         4.0),
    ("Beam X end past mast pocket",     end_wall_x,          3.0),
    ("Pi insert to beam Y edge",        pi_to_edge_y,        2.0),
    ("Pi insert to service opening Y",  pi_to_svc_y,         2.0),
    ("Service opening to mast pocket",  svc_to_pocket_x,     5.0),
    ("Material above mast pocket",      material_above_pocket, 8.0),
]
for label, val, min_ok in checks:
    flag = "OK " if val >= min_ok else "!! "
    print(f"  {flag}{label:42s} {val:6.2f} mm  (min {min_ok})")
print()
print("GEOMETRY:")
print(f"  beam:            {BEAM_LEN_X} x {BEAM_W_Y} x {BEAM_H_Z} mm")
print(f"  mast pockets:    {POCKET_W:.1f} sq x {POCKET_DEPTH}, {CHAMFER_SIZE} lead-in")
print(f"  mast bolts:      2x M5, CB {BOLT_CB_D} x {BOLT_CB_H} TOP")
print(f"  Pi mount grid:   {PI_MOUNT_PCD_X} x {PI_MOUNT_PCD_Y} (Pi Carrier adapts to 58 x 49)")
print(f"  service opening: {SERVICE_OPEN_X} x {SERVICE_OPEN_Y} on TOP")
print(f"  cable channel:   {CABLE_CH_W} x {CABLE_CH_D} on REAR")
print(f"  accessory:       {FRONT_INSERT_COUNT}x M5 inserts on FRONT")
print()

doc = FreeCAD.newDocument(PART_ID)

# ============================================================
# Build beam
# ============================================================
beam = Part.makeBox(BEAM_LEN_X, BEAM_W_Y, BEAM_H_Z,
                    FreeCAD.Vector(-BEAM_LEN_X/2.0, -BEAM_W_Y/2.0, 0))

# Mast capture pockets (cut from bottom)
for mx in MAST_X_POS:
    pocket = Part.makeBox(POCKET_W, POCKET_T, POCKET_DEPTH + EPS_OVERCUT,
                          FreeCAD.Vector(mx - POCKET_W/2.0,
                                          -POCKET_T/2.0, -CUT_START_OFF))
    beam = beam.cut(pocket)
    # V1.2: 1 mm stepped lead-in at entry (bottom face)
    cham = Part.makeBox(POCKET_W + 2 * CHAMFER_SIZE,
                         POCKET_T + 2 * CHAMFER_SIZE,
                         CHAMFER_SIZE + EPS_OVERCUT,
                         FreeCAD.Vector(mx - (POCKET_W + 2 * CHAMFER_SIZE)/2.0,
                                         -(POCKET_T + 2 * CHAMFER_SIZE)/2.0,
                                         -CUT_START_OFF))
    beam = beam.cut(cham)

# Mast through-bolts + top counterbore
for mx in MAST_X_POS:
    beam = cut_cylinder(beam, MAST_BOLT_D, BEAM_H_Z + 2 * CUT_EXTRA,
                         FreeCAD.Vector(mx, 0, -CUT_EXTRA))
    beam = cut_cylinder(beam, BOLT_CB_D, BOLT_CB_H + EPS_OVERCUT,
                         FreeCAD.Vector(mx, 0, BEAM_H_Z - BOLT_CB_H))

# Pi mount inserts (BOTTOM face) -- Pi Carrier adapts to Pi 4 58 x 49
for sx in (-1, +1):
    for sy in (-1, +1):
        hx = sx * (PI_MOUNT_PCD_X / 2.0)
        hy = sy * (PI_MOUNT_PCD_Y / 2.0)
        beam = cut_cylinder(beam, INSERT_POCKET_D, INSERT_POCKET_H,
                             FreeCAD.Vector(hx, hy, -EPS_OVERCUT))

# Cable channel (REAR)
ch = Part.makeBox(CABLE_CH_LEN_X, CABLE_CH_D + EPS_OVERCUT, CABLE_CH_W,
                   FreeCAD.Vector(-CABLE_CH_LEN_X/2.0,
                                   BEAM_W_Y/2.0 - CABLE_CH_D,
                                   (BEAM_H_Z - CABLE_CH_W) / 2.0))
beam = beam.cut(ch)

# Accessory expansion pockets (FRONT)
front_y = -BEAM_W_Y/2.0
total_span = (FRONT_INSERT_COUNT - 1) * FRONT_INSERT_PITCH
x0 = -total_span / 2.0
for i in range(FRONT_INSERT_COUNT):
    hx = x0 + i * FRONT_INSERT_PITCH
    if any(abs(hx - mx) < INSERT_POCKET_D for mx in MAST_X_POS):
        continue
    beam = cut_cylinder(beam, INSERT_POCKET_D, INSERT_POCKET_H,
                         FreeCAD.Vector(hx, front_y - EPS_OVERCUT, FRONT_INSERT_Z),
                         FreeCAD.Vector(0, 1, 0))

# Center service opening (TOP through-cut)
svc = Part.makeBox(SERVICE_OPEN_X, SERVICE_OPEN_Y, BEAM_H_Z + 2 * EPS_OVERCUT,
                    FreeCAD.Vector(-SERVICE_OPEN_X/2.0,
                                    -SERVICE_OPEN_Y/2.0, -EPS_OVERCUT))
beam = beam.cut(svc)

# Export (filenames derived from PART_ID -- no drift on revision)
obj = doc.addObject("Part::Feature", PART_ID)
obj.Shape = beam
if FreeCAD.GuiUp and obj.ViewObject is not None:
    obj.ViewObject.ShapeColor = (0.35, 0.50, 0.85)
doc.recompute()

BASE = os.path.dirname(os.path.dirname(os.path.abspath(__file__)))
OUT_STL  = os.path.join(BASE, PART_ID + ".stl")
OUT_STEP = os.path.join(BASE, PART_ID + ".step")
Part.export([obj], OUT_STL)
Part.export([obj], OUT_STEP)
try:
    com = beam.CenterOfMass
except AttributeError:
    com = beam.Solids[0].CenterOfMass if beam.Solids else None
print(f"[OK] STL:  {OUT_STL}")
print(f"[OK] STEP: {OUT_STEP}")
print(f"     volume: {beam.Volume:.0f} mm^3  (~{beam.Volume*1.27/1000:.1f}g PETG)")
if com is not None:
    print(f"     center of mass (beam-local):  X={com.x:+.2f}  Y={com.y:+.2f}  Z={com.z:+.2f} mm")
print("=" * 70)
