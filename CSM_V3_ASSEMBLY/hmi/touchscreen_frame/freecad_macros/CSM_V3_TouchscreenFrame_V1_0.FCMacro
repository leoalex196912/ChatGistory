# -*- coding: utf-8 -*-
# =============================================================================
# CSM V3 -- MODULE 10 HMI -- TOUCHSCREEN FRAME V1.0 (Part M10-P05)
# =============================================================================
# Back plate that mounts the ELECROW RC070S 7" HDMI touchscreen
# (Amazon B08FMNDDSL, 165 x 100 x 10 mm, 236 g) to the Cross Beam V1.2
# FRONT face.
#
# Mounting flow:
#   1. ELECROW kit: 4 brass pillars thread INTO the screen back
#   2. M2.5 screws pass THROUGH the frame plate INTO the pillars
#   3. The pillar height holds the screen ~5-8 mm off the frame front
#      face -- HDMI / USB / 3.5 mm jacks all live in that gap
#   4. Cables exit through the bottom-edge cutout, route up the rear
#      mast face, into the beam cable channel, to the Pi
#
# Frame interface to beam:
#   4 of the 6 M5 heat-set inserts on the beam FRONT (-Y) face are used
#   (the outer pair + the next-in pair, at X = +/-55 and +/-33 mm).
#   M5 socket-head bolts go through the frame's top TAB BAND into the
#   beam inserts.
#
# Why elongated slots for screen mounting:
#   ELECROW does not publish the RC070S back-panel PCD.  The 4 slots
#   (20 x 10 mm) cover a generous adjustment range so any reasonable
#   4-corner pattern fits without re-drilling.  Once the first install
#   verifies the actual PCD, V1.1 can fix the holes to size.
#
# Local frame:
#   X = along beam width (and across screen long-axis)
#   Y = thickness (+Y = beam side, -Y = operator side)
#   Z = vertical (Z=0 = bottom edge, Z=FRAME_H = top edge)
# =============================================================================

import FreeCAD, Part, math, os, sys
sys.path.insert(0, r"C:\3D-Project\00_PROJECT_OVERVIEW")
import machine_datums as MD

# ============================================================
# PART METADATA (CSM V3 macro standard header)
# ============================================================
PART_NUMBER     = "M10-P05"
PART_NAME       = "Touchscreen Frame"
VERSION         = "V1.0"
STATUS          = "DRAFT"
PART_ID         = "CSM_V3_TouchscreenFrame_V1_0"
PRINT_QTY       = 1
PRINT_MATERIAL  = "PETG (PA12 production)"
PRINT_INFILL    = "100%"
PRINT_LAYER     = "0.20 mm"
PRINT_WALLS     = 4

# ============================================================
# Helpers
# ============================================================
def cut_box(shape, w, d, h, origin):
    box = Part.makeBox(w, d, h, origin)
    return shape.cut(box)

def cut_cylinder(shape, diameter, length, origin, direction=FreeCAD.Vector(0, 0, 1)):
    cyl = Part.makeCylinder(diameter / 2.0, length, origin, direction)
    return shape.cut(cyl)

# ============================================================
# Geometry parameters (all from machine_datums HMI_* block)
# ============================================================
FRAME_W           = MD.HMI_FRAME_W
FRAME_H           = MD.HMI_FRAME_H
FRAME_T           = MD.HMI_FRAME_T
TAB_HEIGHT        = MD.HMI_FRAME_TAB_HEIGHT
BEAM_BOLT_Z_TOP   = MD.HMI_FRAME_BEAM_BOLT_Z

# Screen
TOUCH_W           = MD.HMI_TOUCH_W
TOUCH_H           = MD.HMI_TOUCH_H

# Beam mount: 4 of 6 FRONT-face inserts (skip middle pair)
FRONT_PITCH       = MD.HMI_FRONT_INSERT_PITCH                     # 22
BEAM_BOLT_XS      = (-1.5 * FRONT_PITCH, -2.5 * FRONT_PITCH,      # -33, -55
                     +1.5 * FRONT_PITCH, +2.5 * FRONT_PITCH)      # +33, +55
M5_BOLT_D         = MD.HMI_M5_THROUGH_D

# Screen mount slots
SCREEN_PCD_X      = MD.HMI_TOUCH_PCD_X_NOMINAL
SCREEN_PCD_Y      = MD.HMI_TOUCH_PCD_Y_NOMINAL
SLOT_X            = MD.HMI_TOUCH_SLOT_LEN_X
SLOT_Z            = MD.HMI_TOUCH_SLOT_LEN_Z
M2_5_CLEAR_D      = MD.HMI_M2_5_CLEAR_D

# Cable cutout (bottom edge)
CABLE_CUT_W       = MD.HMI_FRAME_CABLE_CUT_W
CABLE_CUT_H       = MD.HMI_FRAME_CABLE_CUT_H

# Boolean / overcut helpers
EPS_OVERCUT       = MD.HMI_BOOLEAN_OVERCUT
CUT_EXTRA         = MD.HMI_CUT_EXTRA

# Derived: screen vertical centerline (within frame Z)
# Tab band is the top 18 mm; screen seats below it with some breathing gap.
TAB_BAND_BOTTOM_Z = FRAME_H - TAB_HEIGHT                            # 112
SCREEN_TOP_GAP    = 1.0
SCREEN_TOP_Z      = TAB_BAND_BOTTOM_Z - SCREEN_TOP_GAP              # 111
SCREEN_CENTER_Z   = SCREEN_TOP_Z - TOUCH_H / 2.0                    # 61
SLOT_TOP_Z        = SCREEN_CENTER_Z + SCREEN_PCD_Y / 2.0            # 98.5
SLOT_BOT_Z        = SCREEN_CENTER_Z - SCREEN_PCD_Y / 2.0            # 23.5
BEAM_BOLT_Z       = FRAME_H - BEAM_BOLT_Z_TOP                       # 123

# ============================================================
# Standard CSM V3 banner
# ============================================================
print("=" * 70)
print(f"CSM V3   Part {PART_NUMBER}   {PART_NAME}   {VERSION}   [{STATUS}]")
print("=" * 70)
print(f"  Material:   {PRINT_MATERIAL}")
print(f"  Print:      {PRINT_INFILL} infill, {PRINT_WALLS} walls, {PRINT_LAYER} layers")
print(f"  Quantity:   {PRINT_QTY}")
print()
print("WALL-THICKNESS CHECK:")
top_to_beam_bolt        = FRAME_H - BEAM_BOLT_Z - M5_BOLT_D / 2.0       # frame top to bolt edge
beam_bolt_to_tab_bottom = BEAM_BOLT_Z - M5_BOLT_D / 2.0 - TAB_BAND_BOTTOM_Z
side_to_outer_bolt      = FRAME_W / 2.0 - max(abs(x) for x in BEAM_BOLT_XS) - M5_BOLT_D / 2.0
bolt_spacing            = (sorted(BEAM_BOLT_XS)[1] - sorted(BEAM_BOLT_XS)[0]) - M5_BOLT_D
top_to_slot_top         = FRAME_H - (SLOT_TOP_Z + SLOT_Z / 2.0)
bot_to_slot_bot         = (SLOT_BOT_Z - SLOT_Z / 2.0) - CABLE_CUT_H
side_to_slot            = FRAME_W / 2.0 - (SCREEN_PCD_X / 2.0 + SLOT_X / 2.0)
tab_band_to_slot        = TAB_BAND_BOTTOM_Z - (SLOT_TOP_Z + SLOT_Z / 2.0)
checks = [
    ("Top edge to beam bolt (Z)",        top_to_beam_bolt,        3.0),
    ("Beam bolt to tab-band bottom (Z)", beam_bolt_to_tab_bottom, 3.0),
    ("Side edge to outer beam bolt (X)", side_to_outer_bolt,      3.0),
    ("Adjacent beam bolt spacing (X)",   bolt_spacing,            5.0),
    ("Top edge to slot top (Z)",         top_to_slot_top,         3.0),
    ("Slot bottom to cable cutout (Z)",  bot_to_slot_bot,         3.0),
    ("Side edge to slot outer (X)",      side_to_slot,            5.0),
    ("Tab-band bottom to slot top (Z)",  tab_band_to_slot,        2.0),
]
for label, val, min_ok in checks:
    flag = "OK " if val >= min_ok else "!! "
    print(f"  {flag}{label:42s} {val:6.2f} mm  (min {min_ok})")
print()
print("GEOMETRY:")
print(f"  plate:           {FRAME_W} x {FRAME_T} x {FRAME_H} mm")
print(f"  tab band:        top {TAB_HEIGHT} mm")
print(f"  beam mount:      4x M5 at X={BEAM_BOLT_XS}, Z={BEAM_BOLT_Z}")
print(f"  screen window:   nominal PCD {SCREEN_PCD_X} x {SCREEN_PCD_Y}")
print(f"  screen slots:    4x M2.5 elongated, {SLOT_X} x {SLOT_Z} mm")
print(f"                   adjustment range +/-{SLOT_X/2} mm X, +/-{SLOT_Z/2} mm Z")
print(f"  cable cutout:    bottom edge, {CABLE_CUT_W} x {CABLE_CUT_H} mm")
print(f"  screen target:   {TOUCH_W} x {TOUCH_H} (ELECROW RC070S, B08FMNDDSL)")
print()

doc = FreeCAD.newDocument(PART_ID)

# ============================================================
# Build plate
# Origin at front-bottom-center: X = +/-FRAME_W/2, Y = 0 (back) to FRAME_T (front)
# but cleaner to put origin at plate center XZ on back face.
# Actually use: X = +/-FRAME_W/2, Y = -FRAME_T/2 to +FRAME_T/2, Z = 0 to FRAME_H
# Local convention: bottom of plate at Z=0, top at Z=FRAME_H, front at Y=-FRAME_T/2.
# ============================================================
plate = Part.makeBox(FRAME_W, FRAME_T, FRAME_H,
                     FreeCAD.Vector(-FRAME_W/2.0, -FRAME_T/2.0, 0))

# Beam mount through-holes (Y direction = full thickness)
for bx in BEAM_BOLT_XS:
    plate = cut_cylinder(plate, M5_BOLT_D, FRAME_T + 2 * CUT_EXTRA,
                          FreeCAD.Vector(bx, -FRAME_T/2.0 - CUT_EXTRA, BEAM_BOLT_Z),
                          FreeCAD.Vector(0, 1, 0))

# Screen mount slots (elongated rectangles, cut Y full thickness)
for sx in (-1, +1):
    for sz in (-1, +1):
        cx = sx * (SCREEN_PCD_X / 2.0)
        cz = SCREEN_CENTER_Z + sz * (SCREEN_PCD_Y / 2.0)
        # Stadium-ish slot: simple rectangle (FDM-friendly)
        plate = cut_box(plate, SLOT_X, FRAME_T + 2 * EPS_OVERCUT, SLOT_Z,
                         FreeCAD.Vector(cx - SLOT_X/2.0,
                                         -FRAME_T/2.0 - EPS_OVERCUT,
                                         cz - SLOT_Z/2.0))

# Cable cutout (bottom edge, full Y depth)
plate = cut_box(plate, CABLE_CUT_W, FRAME_T + 2 * EPS_OVERCUT, CABLE_CUT_H + EPS_OVERCUT,
                 FreeCAD.Vector(-CABLE_CUT_W/2.0,
                                 -FRAME_T/2.0 - EPS_OVERCUT,
                                 -EPS_OVERCUT))

# Export
obj = doc.addObject("Part::Feature", PART_ID)
obj.Shape = plate
if FreeCAD.GuiUp and obj.ViewObject is not None:
    obj.ViewObject.ShapeColor = (0.45, 0.55, 0.80)
doc.recompute()

BASE = os.path.dirname(os.path.dirname(os.path.abspath(__file__)))
OUT_STL  = os.path.join(BASE, PART_ID + ".stl")
OUT_STEP = os.path.join(BASE, PART_ID + ".step")
Part.export([obj], OUT_STL)
Part.export([obj], OUT_STEP)

try:
    com = plate.CenterOfMass
except AttributeError:
    com = plate.Solids[0].CenterOfMass if plate.Solids else None
print(f"[OK] STL:  {OUT_STL}")
print(f"[OK] STEP: {OUT_STEP}")
print(f"     volume: {plate.Volume:.0f} mm^3  (~{plate.Volume*1.27/1000:.1f}g PETG)")
if com is not None:
    print(f"     center of mass (frame-local):  X={com.x:+.2f}  Y={com.y:+.2f}  Z={com.z:+.2f} mm")
print()
print("ASSEMBLY:")
print(" 1. Print PETG flat on bed, 100% infill, 4 walls, 0.2 mm layers")
print("    (BACK face up so the slot edges print clean)")
print(" 2. Verify the ELECROW RC070S back-panel mounting hole pattern.")
print("    Loosen the 4 M2.5 screws to fit -- the 20x10 slots give")
print("    +/-10 mm X and +/-5 mm Z adjustment.  If your PCD is outside")
print("    that range, update HMI_TOUCH_PCD_X/Y_NOMINAL in machine_datums")
print("    and re-run for V1.1.")
print(" 3. Thread 4x brass pillars (from ELECROW kit) INTO the screen back")
print(" 4. Hold screen behind the frame; pass 4x M2.5 screws THROUGH the")
print("    front face slots INTO the pillars; tighten gently")
print(" 5. Connect HDMI + USB cables to screen (they hide in the pillar gap)")
print(" 6. Route cables DOWN through the bottom-edge cutout")
print(" 7. Bolt 4x M5 x 12 mm socket-head into beam FRONT face inserts")
print("    (at X = +/-33 and +/-55; skip the middle pair)")
print(" 8. Route HDMI + USB up rear mast face into beam cable channel,")
print("    then forward to the Pi Carrier inside the service opening")
print("=" * 70)
